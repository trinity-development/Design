(defun c:REVLIST()
  ;(command "vbaload" "Draw.dvb")
  (setq start (getvar "MILLISECS"))
  (command "-vbarun" "Module1.revisionlist")
  (setq end (getvar "MILLISECS"))
  (princ "\n")
  (princ " revlist time ")
  (princ (itoa (- end start)))
)
