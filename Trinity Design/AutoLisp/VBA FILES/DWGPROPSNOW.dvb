Attribute VB_Name = "Module1"
Sub newarray()
UserForm1.show
End Sub

Attribute VB_Name = "Module2"
Sub propsnow()
UserForm2.show
End Sub

Attribute VB_Name = "UserForm1"
Attribute VB_Base = "0{39E95E1B-4783-4E43-9F3F-42BA96A70A6B}{C029992A-FC3E-4DE1-A1DC-8C80DE1C2C0E}"
Attribute VB_GlobalNameSpace = False
Attribute VB_Creatable = False
Attribute VB_PredeclaredId = True
Attribute VB_Exposed = False
Attribute VB_TemplateDerived = False
Attribute VB_Customizable = False
Private Sub AddRowButton_Click()
    If Row4Frame.Visible = True Then
        Row5Frame.Visible = True
        UserForm1.Height = 610.5
    ElseIf Row3Frame.Visible = True Then
        Row4Frame.Visible = True
        UserForm1.Height = 513
    ElseIf Row2Frame.Visible = True Then
        Row3Frame.Visible = True
        UserForm1.Height = 414.75
    ElseIf Row1Frame.Visible = True Then
        Row2Frame.Visible = True
        UserForm1.Height = 322.5
    Else
    
    End If
    
End Sub

Private Sub LandscapeR1_Click()
    If LandscapeR1.Value = True Then
        PortraitR1.Value = False
    Else
    End If
End Sub

Private Sub LandscapeR2_Click()
    If LandscapeR2.Value = True Then
        PortraitR2.Value = False
    Else
    End If
End Sub

Private Sub LandscapeR3_Click()
    If LandscapeR3.Value = True Then
        PortraitR3.Value = False
    Else
    End If
End Sub

Private Sub LandscapeR4_Click()
    If LandscapeR4.Value = True Then
        PortraitR4.Value = False
    Else
    End If
End Sub

Private Sub LandscapeR5_Click()
    If LandscapeR5.Value = True Then
        PortraitR5.Value = False
    Else
    End If
End Sub



Private Sub PortraitR1_Click()
    If PortraitR1.Value = True Then
        LandscapeR1.Value = False
    Else
    End If
End Sub

Private Sub PortraitR2_Click()
    If PortraitR2.Value = True Then
        LandscapeR2.Value = False
    Else
    End If
End Sub

Private Sub PortraitR3_Click()
    If PortraitR3.Value = True Then
        LandscapeR3.Value = False
    Else
    End If
End Sub

Private Sub PortraitR4_Click()
    If PortraitR4.Value = True Then
        LandscapeR4.Value = False
    Else
    End If
End Sub

Private Sub PortraitR5_Click()
    If PortraitR5.Value = True Then
        LandscapeR5.Value = False
    Else
    End If
End Sub

Public Sub UserForm_Initialize()


Row2Frame.Visible = False
Row3Frame.Visible = False
Row4Frame.Visible = False
Row5Frame.Visible = False
End Sub
Private Sub CloseButton_Click()
Unload Me
UserForm1.Hide
End Sub

Private Sub MakeArrayButton_Click()
    Dim blk As AcadBlockReference
    Dim insertFile As String
    Dim grab(0 To 2) As Double
    Dim inspt(0 To 2) As Double
    Dim bpt(0 To 2) As Double
    Dim nextX As Double
    Dim nextY As Double
    Dim Pi As Double
    regularPanel = App_Path() & "genesis_module.dwg"
    microPanel = App_Path() & "micro_module.dwg"
    path1 = ThisDrawing.Path
    path2 = "\ACAD CALC TEMPLATE.xlsx"
    excelPath = path1 + path2
    
    Set xlapp = CreateObject("excel.application")

    xlapp.Workbooks.Open fileName:=excelPath

    xlapp.Visible = False
    
    If xlapp.Application.cells(6, 6).Value <> "" Then
        insertFile = microPanel
    Else
        insertFile = regularPanel
    End If
    
    xlapp.DisplayAlerts = False

    xlapp.Application.ActiveWorkbook.SaveAs (excelPath)
    xlapp.Quit
    
    nextXport = 40.0625
    nextYport = 65.1875
    nextYland = 40.0625
    nextXland = 65.1875
    Pi = 4 * Atn(1)
    bpt(0) = 2217.25
    bpt(1) = 14491.6875
    bpt(2) = 0
    grab(0) = 3059.3125
    grab(1) = 14491.6875
    grab(2) = 0
    '''''''''''''''''''''''''''''''''''''''''''''''''''''''
    '''''''''''''''''ROW 1'''''''''''''''''''''''''''''''''
    '''''''''''''''''''''''''''''''''''''''''''''''''''''''
    If IsNumeric(TextBox1.Value) = True Then
        inspt(0) = 2331.19
        inspt(1) = 14390.94
        inspt(2) = 0
        ''''''''''''''''''''''''''''''''''''''''''''
        '''''''''''''PORTRAIT PANELS''''''''''''''''
        ''''''''''''''''''''''''''''''''''''''''''''
        If PortraitR1.Value = True Then
            For i = 0 To (TextBox1.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        '''''''''''''''''''''''''''''''''''''''''''''
        ''''''''''''''LANDSCAPE PANELS'''''''''''''''
        '''''''''''''''''''''''''''''''''''''''''''''
        ElseIf LandscapeR1.Value = True Then
            For i = 0 To (TextBox1.Value - 1)
                inspt(0) = inspt(0) + nextXland + 1
                inspt(1) = inspt(1)
                inspt(2) = inspt(2)
                
                Set blk = ThisDrawing.ModelSpace.InsertBlock(inspt, insertFile, 1, 1, 1, 0)
                blk.Rotate inspt, (-90 * Pi / 180)
                blk.Rotate3D bpt, grab, (RoofPitchTextBox.Value * Pi / 180)
            Next i
        Else
        End If
    Else
    End If
    
    
    If IsNumeric(TextBox3.Value) = True Then
        
        ''''''''''''''''''''''''''''''''''''''''''''
        '''''''''''''PORTRAIT PANELS''''''''''''''''
        ''''''''''''''''''''''''''''''''''''''''''''
        
        
        If (PortraitR2.Value = True) And (LandscapeR1.Value = True) Then
        inspt(0) = 2331.19
        inspt(1) = 14390.94 - 52 - 1
        inspt(2) = 0
            For i = 0 To (TextBox3.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        ElseIf PortraitR2.Value = True Then
        inspt(0) = 2331.19
        inspt(1) = 14390.94 - nextYport - 0.25
        inspt(2) = 0
            For i = 0 To (TextBox3.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        '''''''''''''''''''''''''''''''''''''''''''''
        ''''''''''''''LANDSCAPE PANELS'''''''''''''''
        '''''''''''''''''''''''''''''''''''''''''''''
        ElseIf LandscapeR2.Value = True Then
        inspt(0) = 2331.19
        inspt(1) = 14390.94 - nextYland - 0.25
        inspt(2) = 0
            For i = 0 To (TextBox3.Value - 1)
                inspt(0) = inspt(0) + nextXland + 1
                inspt(1) = inspt(1)
                inspt(2) = inspt(2)
                
                Set blk = ThisDrawing.ModelSpace.InsertBlock(inspt, insertFile, 1, 1, 1, 0)
                blk.Rotate inspt, (-90 * Pi / 180)
                blk.Rotate3D bpt, grab, (RoofPitchTextBox.Value * Pi / 180)
            Next i
        Else
        End If
    Else
    End If
    
    
    If IsNumeric(TextBox4.Value) = True Then
        
        ''''''''''''''''''''''''''''''''''''''''''''
        '''''''''''''PORTRAIT PANELS''''''''''''''''
        ''''''''''''''''''''''''''''''''''''''''''''
        
        
        If (PortraitR3.Value = True) And (LandscapeR1.Value = True) Then
        inspt(0) = 2331.19
        inspt(1) = 14390.94 - 2 * 58.75 - 1
            For i = 0 To (TextBox4.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        ElseIf PortraitR3.Value = True Then
        inspt(0) = 2331.19
        inspt(1) = 14390.94 - 2 * nextYport - 0.5
        inspt(2) = 0
            For i = 0 To (TextBox4.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        '''''''''''''''''''''''''''''''''''''''''''''
        ''''''''''''''LANDSCAPE PANELS'''''''''''''''
        '''''''''''''''''''''''''''''''''''''''''''''
        ElseIf LandscapeR3.Value = True Then
        inspt(0) = 2331.19
        inspt(1) = 14390.94 - 2 * nextYland
        inspt(2) = 0
            For i = 0 To (TextBox4.Value - 1)
                inspt(0) = inspt(0) + nextXland + 1
                inspt(1) = inspt(1)
                inspt(2) = inspt(2)
                
                Set blk = ThisDrawing.ModelSpace.InsertBlock(inspt, insertFile, 1, 1, 1, 0)
                blk.Rotate inspt, (-90 * Pi / 180)
                blk.Rotate3D bpt, grab, (RoofPitchTextBox.Value * Pi / 180)
            Next i
        Else
        End If
    Else
    End If
    
    
    If IsNumeric(TextBox5.Value) = True Then
        
        ''''''''''''''''''''''''''''''''''''''''''''
        '''''''''''''PORTRAIT PANELS''''''''''''''''
        ''''''''''''''''''''''''''''''''''''''''''''
        
        
        If (PortraitR4.Value = True) And (LandscapeR1.Value = True) Then
        inspt(0) = 2331.19
        inspt(1) = 14390.94 - 3 * 61 - 1
        inspt(2) = 0
            For i = 0 To (TextBox5.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        ElseIf PortraitR4.Value = True Then
        inspt(0) = 2331.19
        inspt(1) = 14390.94 - 3 * nextYport - 0.75
        inspt(2) = 0
            For i = 0 To (TextBox5.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        '''''''''''''''''''''''''''''''''''''''''''''
        ''''''''''''''LANDSCAPE PANELS'''''''''''''''
        '''''''''''''''''''''''''''''''''''''''''''''
        ElseIf LandscapeR4.Value = True Then
        inspt(0) = 2331.19
        inspt(1) = 14390.94 - 3 * nextYland - 0.25
        inspt(2) = 0
            For i = 0 To (TextBox5.Value - 1)
                inspt(0) = inspt(0) + nextXland + 1
                inspt(1) = inspt(1)
                inspt(2) = inspt(2)
                
                Set blk = ThisDrawing.ModelSpace.InsertBlock(inspt, insertFile, 1, 1, 1, 0)
                blk.Rotate inspt, (-90 * Pi / 180)
                blk.Rotate3D bpt, grab, (RoofPitchTextBox.Value * Pi / 180)
            Next i
        Else
        End If
    Else
    End If
    
    
    If IsNumeric(TextBox6.Value) = True Then
        
        ''''''''''''''''''''''''''''''''''''''''''''
        '''''''''''''PORTRAIT PANELS''''''''''''''''
        ''''''''''''''''''''''''''''''''''''''''''''
        
        
        If (PortraitR5.Value = True) And (LandscapeR1.Value = True) Then
        inspt(0) = 2331.19
        inspt(1) = 14390.94 - 4 * 62.15 - 1
        inspt(2) = 0
            For i = 0 To (TextBox6.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        ElseIf PortraitR5.Value = True Then
        inspt(0) = 2331.19
        inspt(1) = 14390.94 - 4 * nextYport - 1
        inspt(2) = 0
            For i = 0 To (TextBox6.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        '''''''''''''''''''''''''''''''''''''''''''''
        ''''''''''''''LANDSCAPE PANELS'''''''''''''''
        '''''''''''''''''''''''''''''''''''''''''''''
        ElseIf LandscapeR5.Value = True Then
        inspt(0) = 2331.19
        inspt(1) = 14390.94 - 4 * nextYland - 0.5
        inspt(2) = 0
            For i = 0 To (TextBox6.Value - 1)
                inspt(0) = inspt(0) + nextXland + 1
                inspt(1) = inspt(1)
                inspt(2) = inspt(2)
                
                Set blk = ThisDrawing.ModelSpace.InsertBlock(inspt, insertFile, 1, 1, 1, 0)
                blk.Rotate inspt, (-90 * Pi / 180)
                blk.Rotate3D bpt, grab, (RoofPitchTextBox.Value * Pi / 180)
            Next i
        Else
        End If
    Else
    End If
    Unload Me
UserForm1.Hide
End Sub

Public Function App_Path() As String
   Dim str As String
   str = ThisDrawing.Application.VBE.ActiveVBProject.fileName
   App_Path = GetPathFromFilename(str)
End Function

Public Function GetPathFromFilename(sFile) As String
   Dim arr() As String
   arr = Split(sFile, "\", -1, vbTextCompare)
   GetPathFromFilename = Left(sFile, Len(sFile) - Len(arr(UBound(arr))))
End Function

Attribute VB_Name = "UserForm2"
Attribute VB_Base = "0{1ABF6FF8-DB7D-455E-9E15-180686ADE875}{5FCD3F88-1FBC-4D92-A9F6-01E27227B72B}"
Attribute VB_GlobalNameSpace = False
Attribute VB_Creatable = False
Attribute VB_PredeclaredId = True
Attribute VB_Exposed = False
Attribute VB_TemplateDerived = False
Attribute VB_Customizable = False
Private Sub CommandButton1_Click()

ThisDrawing.SummaryInfo.SetCustomByKey "01 serviceAmperage", TextBox1.Value

ThisDrawing.SummaryInfo.SetCustomByKey "02 discoAmperage", TextBox3.Value

ThisDrawing.SummaryInfo.SetCustomByKey "03 overcurruntProtection", TextBox2.Value

ThisDrawing.SummaryInfo.SetCustomByKey "06 nonFused", TextBox5.Value

ThisDrawing.SummaryInfo.SetCustomByKey "unfusedDiscoPartNum", TextBox6.Value

ThisDrawing.SummaryInfo.SetCustomByKey "05 subpanelAmperage", TextBox4.Value

ThisDrawing.SummaryInfo.SetCustomByKey "04 inv1", TextBox7.Value

ThisDrawing.SummaryInfo.SetCustomByKey "04 inv2", TextBox8.Value

ThisDrawing.SummaryInfo.SetCustomByKey "04 inv3", TextBox9.Value

ThisDrawing.SummaryInfo.SetCustomByKey "04 inv4", TextBox10.Value

ThisDrawing.SummaryInfo.SetCustomByKey "04 inv5", TextBox11.Value

ThisDrawing.SummaryInfo.SetCustomByKey "04 micro1", TextBox12.Value

ThisDrawing.SummaryInfo.SetCustomByKey "04 micro2", TextBox13.Value

ThisDrawing.SummaryInfo.SetCustomByKey "04 micro3", TextBox14.Value

ThisDrawing.SummaryInfo.SetCustomByKey "04 micro4", TextBox15.Value

ThisDrawing.SummaryInfo.SetCustomByKey "04 micro5", TextBox16.Value

ThisDrawing.SummaryInfo.SetCustomByKey "fusedDiscoPartNum", TextBox18.Value

ThisDrawing.SummaryInfo.SetCustomByKey "BusbarAmperage", TextBox17.Value

ThisDrawing.SummaryInfo.SetCustomByKey "maxroof", TextBox19.Value

ThisDrawing.SendCommand ("regen" & vbCr)
Unload Me
UserForm1.Hide
End Sub

Private Sub ToggleButton1_Click()
    If ToggleButton1.Value = False Then
        ToggleButton1.Caption = "Press for Micros"
        Label8.Visible = True
        TextBox7.Visible = True
        Label9.Visible = True
        TextBox8.Visible = True
        Label10.Visible = True
        TextBox9.Visible = True
        Label11.Visible = True
        TextBox10.Visible = True
        Label12.Visible = True
        TextBox11.Visible = True
        
        Label13.Visible = False
        TextBox12.Visible = False
        Label14.Visible = False
        TextBox13.Visible = False
        Label15.Visible = False
        TextBox14.Visible = False
        Label16.Visible = False
        TextBox15.Visible = False
        Label21.Visible = False
        TextBox16.Visible = False
    Else
    End If
    
    If ToggleButton1.Value = True Then
        ToggleButton1.Caption = "Press For SolarEdge"
        Label13.Visible = True
        TextBox12.Visible = True
        Label14.Visible = True
        TextBox13.Visible = True
        Label15.Visible = True
        TextBox14.Visible = True
        Label16.Visible = True
        TextBox15.Visible = True
        Label21.Visible = True
        TextBox16.Visible = True
        
        Label8.Visible = False
        TextBox7.Visible = False
        Label9.Visible = False
        TextBox8.Visible = False
        Label10.Visible = False
        TextBox9.Visible = False
        Label11.Visible = False
        TextBox10.Visible = False
        Label12.Visible = False
        TextBox11.Visible = False
    Else
    End If
End Sub

Private Sub UserForm_Initialize()
Dim servamp As String
Dim discoamp As String
Dim OCPDamp As String
Dim nonfusedamp As String
Dim nonfusedPN As String
Dim subpanelamp As String
Dim inv1 As String
Dim inv2 As String
Dim inv3 As String
Dim inv4 As String
Dim inv5 As String
Dim micro1 As String
Dim micro2 As String
Dim micro3 As String
Dim micro4 As String
Dim micro5 As String
Dim discoPartNum As String
Dim busbar As String
Dim maxrf As String
Label13.Visible = False
TextBox12.Visible = False
Label14.Visible = False
TextBox13.Visible = False
Label15.Visible = False
TextBox14.Visible = False
Label16.Visible = False
TextBox15.Visible = False
Label21.Visible = False
TextBox16.Visible = False
        
ThisDrawing.SummaryInfo.GetCustomByKey "01 serviceAmperage", servamp
TextBox1.Value = servamp

ThisDrawing.SummaryInfo.GetCustomByKey "02 discoAmperage", discoamp
TextBox3.Value = discoamp

ThisDrawing.SummaryInfo.GetCustomByKey "03 overcurruntProtection", OCPDamp
TextBox2.Value = OCPDamp

ThisDrawing.SummaryInfo.GetCustomByKey "06 nonFused", nonfusedamp
TextBox5.Value = nonfusedamp

ThisDrawing.SummaryInfo.GetCustomByKey "unfusedDiscoPartNum", nonfusedPN
TextBox6.Value = nonfusedPN

ThisDrawing.SummaryInfo.GetCustomByKey "05 subpanelAmperage", subpanelamp
TextBox4.Value = subpanelamp

ThisDrawing.SummaryInfo.GetCustomByKey "04 inv1", inv1
TextBox7.Value = inv1

ThisDrawing.SummaryInfo.GetCustomByKey "04 inv2", inv2
TextBox8.Value = inv2

ThisDrawing.SummaryInfo.GetCustomByKey "04 inv3", inv3
TextBox9.Value = inv3

ThisDrawing.SummaryInfo.GetCustomByKey "04 inv4", inv4
TextBox10.Value = inv4

ThisDrawing.SummaryInfo.GetCustomByKey "04 inv5", inv5
TextBox11.Value = inv5

ThisDrawing.SummaryInfo.GetCustomByKey "04 micro1", micro1
TextBox12.Value = micro1

ThisDrawing.SummaryInfo.GetCustomByKey "04 micro2", micro2
TextBox13.Value = micro2

ThisDrawing.SummaryInfo.GetCustomByKey "04 micro3", micro3
TextBox14.Value = micro3

ThisDrawing.SummaryInfo.GetCustomByKey "04 micro4", micro4
TextBox15.Value = micro4

ThisDrawing.SummaryInfo.GetCustomByKey "04 micro5", micro5
TextBox16.Value = micro5

ThisDrawing.SummaryInfo.GetCustomByKey "fusedDiscoPartNum", discoPartNum
TextBox18.Value = discoPartNum

ThisDrawing.SummaryInfo.GetCustomByKey "BusbarAmperage", busbar
TextBox17.Value = busbar

ThisDrawing.SummaryInfo.GetCustomByKey "maxroof", maxrf
TextBox19.Value = maxrf
End Sub
