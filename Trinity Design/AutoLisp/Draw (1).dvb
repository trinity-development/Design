Attribute VB_Name = "Module1"
Sub newarray()
UserForm1.show
End Sub

Attribute VB_Name = "UserForm1"
Attribute VB_Base = "0{61469B71-09F1-4BF3-90C1-9883C0898146}{31C12519-FFAB-4EC6-8D54-364C21213C79}"
Attribute VB_GlobalNameSpace = False
Attribute VB_Creatable = False
Attribute VB_PredeclaredId = True
Attribute VB_Exposed = False
Attribute VB_TemplateDerived = False
Attribute VB_Customizable = False
Private Sub AddRowButton_Click()
    If Row4Frame.Visible = True Then
        Row5Frame.Visible = True
        UserForm1.Height = 610.5
    ElseIf Row3Frame.Visible = True Then
        Row4Frame.Visible = True
        UserForm1.Height = 513
    ElseIf Row2Frame.Visible = True Then
        Row3Frame.Visible = True
        UserForm1.Height = 414.75
    ElseIf Row1Frame.Visible = True Then
        Row2Frame.Visible = True
        UserForm1.Height = 322.5
    Else
    
    End If
    
End Sub

Private Sub LandscapeR1_Click()
    If LandscapeR1.Value = True Then
        PortraitR1.Value = False
    Else
    End If
End Sub

Private Sub LandscapeR2_Click()
    If LandscapeR2.Value = True Then
        PortraitR2.Value = False
    Else
    End If
End Sub

Private Sub LandscapeR3_Click()
    If LandscapeR3.Value = True Then
        PortraitR3.Value = False
    Else
    End If
End Sub

Private Sub LandscapeR4_Click()
    If LandscapeR4.Value = True Then
        PortraitR4.Value = False
    Else
    End If
End Sub

Private Sub LandscapeR5_Click()
    If LandscapeR5.Value = True Then
        PortraitR5.Value = False
    Else
    End If
End Sub



Private Sub PortraitR1_Click()
    If PortraitR1.Value = True Then
        LandscapeR1.Value = False
    Else
    End If
End Sub

Private Sub PortraitR2_Click()
    If PortraitR2.Value = True Then
        LandscapeR2.Value = False
    Else
    End If
End Sub

Private Sub PortraitR3_Click()
    If PortraitR3.Value = True Then
        LandscapeR3.Value = False
    Else
    End If
End Sub

Private Sub PortraitR4_Click()
    If PortraitR4.Value = True Then
        LandscapeR4.Value = False
    Else
    End If
End Sub

Private Sub PortraitR5_Click()
    If PortraitR5.Value = True Then
        LandscapeR5.Value = False
    Else
    End If
End Sub

Public Sub UserForm_Initialize()


Row2Frame.Visible = False
Row3Frame.Visible = False
Row4Frame.Visible = False
Row5Frame.Visible = False
End Sub
Private Sub CloseButton_Click()
Unload Me
UserForm1.Hide
End Sub

Private Sub MakeArrayButton_Click()
    Dim blk As AcadBlockReference
    Dim insertFile As String
    Dim grab(0 To 2) As Double
    Dim inspt(0 To 2) As Double
    Dim bpt(0 To 2) As Double
    Dim nextX As Double
    Dim nextY As Double
    Dim Pi As Double
    regularPanel = App_Path() & "genesis_module.dwg"
    microPanel = App_Path() & "micro_module.dwg"
    path1 = ThisDrawing.Path
    path2 = "\ACAD CALC TEMPLATE.xlsx"
    excelPath = path1 + path2
    
    Set xlapp = CreateObject("excel.application")

    xlapp.Workbooks.Open fileName:=excelPath

    xlapp.Visible = False
    
    If xlapp.Application.cells(6, 6).Value <> "" Then
        insertFile = microPanel
    Else
        insertFile = regularPanel
    End If
    
    xlapp.DisplayAlerts = False

    xlapp.Application.ActiveWorkbook.SaveAs (excelPath)
    xlapp.Quit
    
    nextXport = 40.0625
    nextYport = 65.1875
    nextYland = 40.0625
    nextXland = 65.1875
    Pi = 4 * Atn(1)
    bpt(0) = 2217.25
    bpt(1) = 14491.6875
    bpt(2) = 0
    grab(0) = 3059.3125
    grab(1) = 14491.6875
    grab(2) = 0
    '''''''''''''''''''''''''''''''''''''''''''''''''''''''
    '''''''''''''''''ROW 1'''''''''''''''''''''''''''''''''
    '''''''''''''''''''''''''''''''''''''''''''''''''''''''
    If IsNumeric(TextBox1.Value) = True Then
        inspt(0) = 2331.19
        inspt(1) = 14390.94
        inspt(2) = 0
        ''''''''''''''''''''''''''''''''''''''''''''
        '''''''''''''PORTRAIT PANELS''''''''''''''''
        ''''''''''''''''''''''''''''''''''''''''''''
        If PortraitR1.Value = True Then
            For i = 0 To (TextBox1.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        '''''''''''''''''''''''''''''''''''''''''''''
        ''''''''''''''LANDSCAPE PANELS'''''''''''''''
        '''''''''''''''''''''''''''''''''''''''''''''
        ElseIf LandscapeR1.Value = True Then
            For i = 0 To (TextBox1.Value - 1)
                inspt(0) = inspt(0) + nextXland + 1
                inspt(1) = inspt(1)
                inspt(2) = inspt(2)
                
                Set blk = ThisDrawing.ModelSpace.InsertBlock(inspt, insertFile, 1, 1, 1, 0)
                blk.Rotate inspt, (-90 * Pi / 180)
                blk.Rotate3D bpt, grab, (RoofPitchTextBox.Value * Pi / 180)
            Next i
        Else
        End If
    Else
    End If
    
    
    If IsNumeric(TextBox3.Value) = True Then
        
        ''''''''''''''''''''''''''''''''''''''''''''
        '''''''''''''PORTRAIT PANELS''''''''''''''''
        ''''''''''''''''''''''''''''''''''''''''''''
        
        
        If (PortraitR2.Value = True) And (LandscapeR1.Value = True) Then
        inspt(0) = 2331.19
        inspt(1) = 14390.94 - 52 - 1
        inspt(2) = 0
            For i = 0 To (TextBox3.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        ElseIf PortraitR2.Value = True Then
        inspt(0) = 2331.19
        inspt(1) = 14390.94 - nextYport - 0.25
        inspt(2) = 0
            For i = 0 To (TextBox3.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        '''''''''''''''''''''''''''''''''''''''''''''
        ''''''''''''''LANDSCAPE PANELS'''''''''''''''
        '''''''''''''''''''''''''''''''''''''''''''''
        ElseIf LandscapeR2.Value = True Then
        inspt(0) = 2331.19
        inspt(1) = 14390.94 - nextYland - 0.25
        inspt(2) = 0
            For i = 0 To (TextBox3.Value - 1)
                inspt(0) = inspt(0) + nextXland + 1
                inspt(1) = inspt(1)
                inspt(2) = inspt(2)
                
                Set blk = ThisDrawing.ModelSpace.InsertBlock(inspt, insertFile, 1, 1, 1, 0)
                blk.Rotate inspt, (-90 * Pi / 180)
                blk.Rotate3D bpt, grab, (RoofPitchTextBox.Value * Pi / 180)
            Next i
        Else
        End If
    Else
    End If
    
    
    If IsNumeric(TextBox4.Value) = True Then
        
        ''''''''''''''''''''''''''''''''''''''''''''
        '''''''''''''PORTRAIT PANELS''''''''''''''''
        ''''''''''''''''''''''''''''''''''''''''''''
        
        
        If (PortraitR3.Value = True) And (LandscapeR1.Value = True) Then
        inspt(0) = 2331.19
        inspt(1) = 14390.94 - 2 * 58.75 - 1
            For i = 0 To (TextBox4.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        ElseIf PortraitR3.Value = True Then
        inspt(0) = 2331.19
        inspt(1) = 14390.94 - 2 * nextYport - 0.5
        inspt(2) = 0
            For i = 0 To (TextBox4.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        '''''''''''''''''''''''''''''''''''''''''''''
        ''''''''''''''LANDSCAPE PANELS'''''''''''''''
        '''''''''''''''''''''''''''''''''''''''''''''
        ElseIf LandscapeR3.Value = True Then
        inspt(0) = 2331.19
        inspt(1) = 14390.94 - 2 * nextYland
        inspt(2) = 0
            For i = 0 To (TextBox4.Value - 1)
                inspt(0) = inspt(0) + nextXland + 1
                inspt(1) = inspt(1)
                inspt(2) = inspt(2)
                
                Set blk = ThisDrawing.ModelSpace.InsertBlock(inspt, insertFile, 1, 1, 1, 0)
                blk.Rotate inspt, (-90 * Pi / 180)
                blk.Rotate3D bpt, grab, (RoofPitchTextBox.Value * Pi / 180)
            Next i
        Else
        End If
    Else
    End If
    
    
    If IsNumeric(TextBox5.Value) = True Then
        
        ''''''''''''''''''''''''''''''''''''''''''''
        '''''''''''''PORTRAIT PANELS''''''''''''''''
        ''''''''''''''''''''''''''''''''''''''''''''
        
        
        If (PortraitR4.Value = True) And (LandscapeR1.Value = True) Then
        inspt(0) = 2331.19
        inspt(1) = 14390.94 - 3 * 61 - 1
        inspt(2) = 0
            For i = 0 To (TextBox5.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        ElseIf PortraitR4.Value = True Then
        inspt(0) = 2331.19
        inspt(1) = 14390.94 - 3 * nextYport - 0.75
        inspt(2) = 0
            For i = 0 To (TextBox5.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        '''''''''''''''''''''''''''''''''''''''''''''
        ''''''''''''''LANDSCAPE PANELS'''''''''''''''
        '''''''''''''''''''''''''''''''''''''''''''''
        ElseIf LandscapeR4.Value = True Then
        inspt(0) = 2331.19
        inspt(1) = 14390.94 - 3 * nextYland - 0.25
        inspt(2) = 0
            For i = 0 To (TextBox5.Value - 1)
                inspt(0) = inspt(0) + nextXland + 1
                inspt(1) = inspt(1)
                inspt(2) = inspt(2)
                
                Set blk = ThisDrawing.ModelSpace.InsertBlock(inspt, insertFile, 1, 1, 1, 0)
                blk.Rotate inspt, (-90 * Pi / 180)
                blk.Rotate3D bpt, grab, (RoofPitchTextBox.Value * Pi / 180)
            Next i
        Else
        End If
    Else
    End If
    
    
    If IsNumeric(TextBox6.Value) = True Then
        
        ''''''''''''''''''''''''''''''''''''''''''''
        '''''''''''''PORTRAIT PANELS''''''''''''''''
        ''''''''''''''''''''''''''''''''''''''''''''
        
        
        If (PortraitR5.Value = True) And (LandscapeR1.Value = True) Then
        inspt(0) = 2331.19
        inspt(1) = 14390.94 - 4 * 62.15 - 1
        inspt(2) = 0
            For i = 0 To (TextBox6.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        ElseIf PortraitR5.Value = True Then
        inspt(0) = 2331.19
        inspt(1) = 14390.94 - 4 * nextYport - 1
        inspt(2) = 0
            For i = 0 To (TextBox6.Value - 1)
                inspt(0) = inspt(0) + nextXport + 1
                inspt(1) = inspt(1)
                inspt(2) = inspt(2)
                
                Set blk = ThisDrawing.ModelSpace.InsertBlock(inspt, insertFile, 1, 1, 1, 0)
                blk.Rotate3D bpt, grab, (RoofPitchTextBox.Value * Pi / 180)
            Next i
        '''''''''''''''''''''''''''''''''''''''''''''
        ''''''''''''''LANDSCAPE PANELS'''''''''''''''
        '''''''''''''''''''''''''''''''''''''''''''''
        ElseIf LandscapeR5.Value = True Then
        inspt(0) = 2331.19
        inspt(1) = 14390.94 - 4 * nextYland - 0.5
        inspt(2) = 0
            For i = 0 To (TextBox6.Value - 1)
                inspt(0) = inspt(0) + nextXland + 1
                inspt(1) = inspt(1)
                inspt(2) = inspt(2)
                
                Set blk = ThisDrawing.ModelSpace.InsertBlock(inspt, insertFile, 1, 1, 1, 0)
                blk.Rotate inspt, (-90 * Pi / 180)
                blk.Rotate3D bpt, grab, (RoofPitchTextBox.Value * Pi / 180)
            Next i
        Else
        End If
    Else
    End If
    Unload Me
UserForm1.Hide
End Sub

Public Function App_Path() As String
   Dim str As String
   str = ThisDrawing.Application.VBE.ActiveVBProject.fileName
   App_Path = GetPathFromFilename(str)
End Function

Public Function GetPathFromFilename(sFile) As String
   Dim arr() As String
   arr = Split(sFile, "\", -1, vbTextCompare)
   GetPathFromFilename = Left(sFile, Len(sFile) - Len(arr(UBound(arr))))
End Function
