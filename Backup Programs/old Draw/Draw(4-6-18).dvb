Attribute VB_Name = "Dictionary"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
Attribute VB_Description = "Drop-in replacement for Scripting.Dictionary on Mac\r\n\r\nDictionary v1.4.0\r\n(c) Tim Hall - https://github.com/timhall/VBA-Dictionary\r\nAuthor: tim.hall.engr@gmail.com\r\nLicense: MIT (http://www.opensource.org/licenses/mit-license.php)\r\n"
''
' Dictionary v1.4.1
' (c) Tim Hall - https://github.com/timhall/VBA-Dictionary
'
' Drop-in replacement for Scripting.Dictionary on Mac
'
' @author: tim.hall.engr@gmail.com
' @license: MIT (http://www.opensource.org/licenses/mit-license.php
'
' ~~~~~~~~~~~~~~~~~~~~~~~~~~~~~~~~~~~~~~~~~~~~~~~~~~~~~~~~~~~~~~~~~~~~~~ '
Option Explicit

' --------------------------------------------- '
' Constants and Private Variables
' --------------------------------------------- '

#Const UseScriptingDictionaryIfAvailable = True

#If Mac Or Not UseScriptingDictionaryIfAvailable Then

' dict_KeyValue 0: FormattedKey, 1: OriginalKey, 2: Value
Private dict_pKeyValues As Collection
Private dict_pKeys() As Variant
Private dict_pItems() As Variant
Private dict_pObjectKeys As Collection
Private dict_pCompareMode As CompareMethod

#Else

Private dict_pDictionary As Object

#End If

' --------------------------------------------- '
' Types
' --------------------------------------------- '

Public Enum CompareMethod
    BinaryCompare = VBA.vbBinaryCompare
    TextCompare = VBA.vbTextCompare
    DatabaseCompare = VBA.vbDatabaseCompare
End Enum

' --------------------------------------------- '
' Properties
' --------------------------------------------- '

Public Property Get CompareMode() As CompareMethod
Attribute CompareMode.VB_Description = "Set or get the string comparison method."
#If Mac Or Not UseScriptingDictionaryIfAvailable Then
    CompareMode = dict_pCompareMode
#Else
    CompareMode = dict_pDictionary.CompareMode
#End If
End Property
Public Property Let CompareMode(Value As CompareMethod)
#If Mac Or Not UseScriptingDictionaryIfAvailable Then
    If Me.Count > 0 Then
        ' Can't change CompareMode for Dictionary that contains data
        ' http://msdn.microsoft.com/en-us/library/office/gg278481(v=office.15).aspx
        Err.Raise 5 ' Invalid procedure call or argument
    End If

    dict_pCompareMode = Value
#Else
    dict_pDictionary.CompareMode = Value
#End If
End Property

Public Property Get Count() As Long
Attribute Count.VB_Description = "Get the number of items in the dictionary.\n"
#If Mac Or Not UseScriptingDictionaryIfAvailable Then
    Count = dict_pKeyValues.Count
#Else
    Count = dict_pDictionary.Count
#End If
End Property

Public Property Get Item(Key As Variant) As Variant
Attribute Item.VB_Description = "Set or get the item for a given key."
Attribute Item.VB_UserMemId = 0
#If Mac Or Not UseScriptingDictionaryIfAvailable Then
    Dim dict_KeyValue As Variant
    dict_KeyValue = dict_GetKeyValue(Key)

    If Not IsEmpty(dict_KeyValue) Then
        If VBA.IsObject(dict_KeyValue(2)) Then
            Set Item = dict_KeyValue(2)
        Else
            Item = dict_KeyValue(2)
        End If
    Else
        ' Not found -> Returns Empty
    End If
#Else
    If VBA.IsObject(dict_pDictionary.Item(Key)) Then
        Set Item = dict_pDictionary.Item(Key)
    Else
        Item = dict_pDictionary.Item(Key)
    End If
#End If
End Property
Public Property Let Item(Key As Variant, Value As Variant)
#If Mac Or Not UseScriptingDictionaryIfAvailable Then
    If Me.Exists(Key) Then
        dict_ReplaceKeyValue dict_GetKeyValue(Key), Key, Value
    Else
        dict_AddKeyValue Key, Value
    End If
#Else
    dict_pDictionary.Item(Key) = Value
#End If
End Property
Public Property Set Item(Key As Variant, Value As Variant)
#If Mac Or Not UseScriptingDictionaryIfAvailable Then
    If Me.Exists(Key) Then
        dict_ReplaceKeyValue dict_GetKeyValue(Key), Key, Value
    Else
        dict_AddKeyValue Key, Value
    End If
#Else
    Set dict_pDictionary.Item(Key) = Value
#End If
End Property

Public Property Let Key(Previous As Variant, Updated As Variant)
Attribute Key.VB_Description = "Change a key to a different key."
#If Mac Or Not UseScriptingDictionaryIfAvailable Then
    Dim dict_KeyValue As Variant
    dict_KeyValue = dict_GetKeyValue(Previous)

    If Not VBA.IsEmpty(dict_KeyValue) Then
        dict_ReplaceKeyValue dict_KeyValue, Updated, dict_KeyValue(2)
    End If
#Else
    dict_pDictionary.Key(Previous) = Updated
#End If
End Property

' ============================================= '
' Public Methods
' ============================================= '

''
' Add an item with the given key
'
' @param {Variant} Key
' @param {Variant} Item
' --------------------------------------------- '
Public Sub Add(Key As Variant, Item As Variant)
Attribute Add.VB_Description = "Add a new key and item to the dictionary."
#If Mac Or Not UseScriptingDictionaryIfAvailable Then
    If Not Me.Exists(Key) Then
        dict_AddKeyValue Key, Item
    Else
        ' This key is already associated with an element of this collection
        Err.Raise 457
    End If
#Else
    dict_pDictionary.Add Key, Item
#End If
End Sub

''
' Check if an item exists for the given key
'
' @param {Variant} Key
' @return {Boolean}
' --------------------------------------------- '
Public Function Exists(Key As Variant) As Boolean
Attribute Exists.VB_Description = "Determine if a given key is in the dictionary."
#If Mac Or Not UseScriptingDictionaryIfAvailable Then
    Exists = Not IsEmpty(dict_GetKeyValue(Key))
#Else
    Exists = dict_pDictionary.Exists(Key)
#End If
End Function

''
' Get an array of all items
'
' @return {Variant}
' --------------------------------------------- '
Public Function Items() As Variant
Attribute Items.VB_Description = "Get an array containing all items in the dictionary."
#If Mac Or Not UseScriptingDictionaryIfAvailable Then
    If Me.Count > 0 Then
        Items = dict_pItems
    Else
        ' Split("") creates initialized empty array that matches Dictionary Keys and Items
        Items = VBA.Split("")
    End If
#Else
    Items = dict_pDictionary.Items
#End If
End Function

''
' Get an array of all keys
'
' @return {Variant}
' --------------------------------------------- '
Public Function Keys() As Variant
Attribute Keys.VB_Description = "Get an array containing all keys in the dictionary."
#If Mac Or Not UseScriptingDictionaryIfAvailable Then
    If Me.Count > 0 Then
        Keys = dict_pKeys
    Else
        ' Split("") creates initialized empty array that matches Dictionary Keys and Items
        Keys = VBA.Split("")
    End If
#Else
    Keys = dict_pDictionary.Keys
#End If
End Function

''
' Remove an item for the given key
'
' @param {Variant} Key
' --------------------------------------------- '
Public Sub Remove(Key As Variant)
Attribute Remove.VB_Description = "Remove a given key from the dictionary."
#If Mac Or Not UseScriptingDictionaryIfAvailable Then
    Dim dict_KeyValue As Variant
    dict_KeyValue = dict_GetKeyValue(Key)

    If Not VBA.IsEmpty(dict_KeyValue) Then
        dict_RemoveKeyValue dict_KeyValue
    Else
        ' Application-defined or object-defined error
        Err.Raise 32811
    End If
#Else
    dict_pDictionary.Remove Key
#End If
End Sub

''
' Remove all items
' --------------------------------------------- '
Public Sub RemoveAll()
Attribute RemoveAll.VB_Description = "Remove all information from the dictionary."
#If Mac Or Not UseScriptingDictionaryIfAvailable Then
    Set dict_pKeyValues = New Collection

    Erase dict_pKeys
    Erase dict_pItems
#Else
    dict_pDictionary.RemoveAll
#End If
End Sub

' ============================================= '
' Private Functions
' ============================================= '

#If Mac Or Not UseScriptingDictionaryIfAvailable Then

Private Function dict_GetKeyValue(dict_Key As Variant) As Variant
    On Error Resume Next
    dict_GetKeyValue = dict_pKeyValues(dict_GetFormattedKey(dict_Key))
    Err.Clear
End Function

Private Sub dict_AddKeyValue(dict_Key As Variant, dict_Value As Variant, Optional dict_Index As Long = -1)
    If Me.Count = 0 Then
        ReDim dict_pKeys(0 To 0)
        ReDim dict_pItems(0 To 0)
    Else
        ReDim Preserve dict_pKeys(0 To UBound(dict_pKeys) + 1)
        ReDim Preserve dict_pItems(0 To UBound(dict_pItems) + 1)
    End If

    Dim dict_FormattedKey As String
    dict_FormattedKey = dict_GetFormattedKey(dict_Key)

    If dict_Index >= 0 And dict_Index < dict_pKeyValues.Count Then
        ' Shift keys/items after + including index into empty last slot
        Dim dict_i As Long
        For dict_i = UBound(dict_pKeys) To dict_Index + 1 Step -1
            dict_pKeys(dict_i) = dict_pKeys(dict_i - 1)
            If VBA.IsObject(dict_pItems(dict_i - 1)) Then
                Set dict_pItems(dict_i) = dict_pItems(dict_i - 1)
            Else
                dict_pItems(dict_i) = dict_pItems(dict_i - 1)
            End If
        Next dict_i

        ' Add key/item at index
        dict_pKeys(dict_Index) = dict_Key
        If VBA.IsObject(dict_Value) Then
            Set dict_pItems(dict_Index) = dict_Value
        Else
            dict_pItems(dict_Index) = dict_Value
        End If

        ' Add key-value at proper index
        dict_pKeyValues.Add Array(dict_FormattedKey, dict_Key, dict_Value), dict_FormattedKey, Before:=dict_Index + 1
    Else
        ' Add key-value as last item
        If VBA.IsObject(dict_Key) Then
            Set dict_pKeys(UBound(dict_pKeys)) = dict_Key
        Else
            dict_pKeys(UBound(dict_pKeys)) = dict_Key
        End If
        If VBA.IsObject(dict_Value) Then
            Set dict_pItems(UBound(dict_pItems)) = dict_Value
        Else
            dict_pItems(UBound(dict_pItems)) = dict_Value
        End If

        dict_pKeyValues.Add Array(dict_FormattedKey, dict_Key, dict_Value), dict_FormattedKey
    End If
End Sub

Private Sub dict_ReplaceKeyValue(dict_KeyValue As Variant, dict_Key As Variant, dict_Value As Variant)
    Dim dict_Index As Long
    Dim dict_i As Integer

    dict_Index = dict_GetKeyIndex(dict_KeyValue(1))

    ' Remove existing dict_Value
    dict_RemoveKeyValue dict_KeyValue, dict_Index

    ' Add new dict_Key dict_Value back
    dict_AddKeyValue dict_Key, dict_Value, dict_Index
End Sub

Private Sub dict_RemoveKeyValue(dict_KeyValue As Variant, Optional ByVal dict_Index As Long = -1)
    Dim dict_i As Long
    If dict_Index = -1 Then
        dict_Index = dict_GetKeyIndex(dict_KeyValue(1))
    End If

    If dict_Index >= 0 And dict_Index <= UBound(dict_pKeys) Then
        ' Shift keys/items after index down
        For dict_i = dict_Index To UBound(dict_pKeys) - 1
            dict_pKeys(dict_i) = dict_pKeys(dict_i + 1)

            If VBA.IsObject(dict_pItems(dict_i + 1)) Then
                Set dict_pItems(dict_i) = dict_pItems(dict_i + 1)
            Else
                dict_pItems(dict_i) = dict_pItems(dict_i + 1)
            End If
        Next dict_i

        ' Resize keys/items to remove empty slot
        If UBound(dict_pKeys) = 0 Then
            Erase dict_pKeys
            Erase dict_pItems
        Else
            ReDim Preserve dict_pKeys(0 To UBound(dict_pKeys) - 1)
            ReDim Preserve dict_pItems(0 To UBound(dict_pItems) - 1)
        End If
    End If

    dict_pKeyValues.Remove dict_KeyValue(0)
    dict_RemoveObjectKey dict_KeyValue(1)
End Sub

Private Function dict_GetFormattedKey(dict_Key As Variant) As String
    If VBA.IsObject(dict_Key) Then
        dict_GetFormattedKey = dict_GetObjectKey(dict_Key)
    ElseIf VarType(dict_Key) = VBA.vbBoolean Then
        dict_GetFormattedKey = IIf(dict_Key, "-1__-1", "0__0")
    ElseIf VarType(dict_Key) = VBA.vbString Then
        dict_GetFormattedKey = dict_Key

        If Me.CompareMode = CompareMethod.BinaryCompare Then
            ' Collection does not have method of setting key comparison
            ' So case-sensitive keys aren't supported by default
            ' -> Approach: Append lowercase characters to original key
            '    AbC -> AbC___b_, abc -> abc__abc, ABC -> ABC_____
            Dim dict_Lowercase As String
            dict_Lowercase = ""

            Dim dict_i As Integer
            Dim dict_Char As String
            Dim dict_Ascii As Integer
            For dict_i = 1 To VBA.Len(dict_GetFormattedKey)
                dict_Char = VBA.Mid$(dict_GetFormattedKey, dict_i, 1)
                dict_Ascii = VBA.Asc(dict_Char)
                If dict_Ascii >= 97 And dict_Ascii <= 122 Then
                    dict_Lowercase = dict_Lowercase & dict_Char
                Else
                    dict_Lowercase = dict_Lowercase & "_"
                End If
            Next dict_i

            If dict_Lowercase <> "" Then
                dict_GetFormattedKey = dict_GetFormattedKey & "__" & dict_Lowercase
            End If
        End If
    Else
        ' For numbers, add duplicate to distinguish from strings
        ' ->  123  -> "123__123"
        '    "123" -> "123"
        dict_GetFormattedKey = VBA.CStr(dict_Key) & "__" & CStr(dict_Key)
    End If
End Function

Private Function dict_GetObjectKey(dict_ObjKey As Variant) As String
    Dim dict_i As Integer
    For dict_i = 1 To dict_pObjectKeys.Count
        If dict_pObjectKeys.Item(dict_i) Is dict_ObjKey Then
            dict_GetObjectKey = "__object__" & dict_i
            Exit Function
        End If
    Next dict_i

    dict_pObjectKeys.Add dict_ObjKey
    dict_GetObjectKey = "__object__" & dict_pObjectKeys.Count
End Function

Private Sub dict_RemoveObjectKey(dict_ObjKey As Variant)
    Dim dict_i As Integer
    For dict_i = 1 To dict_pObjectKeys.Count
        If dict_pObjectKeys.Item(dict_i) Is dict_ObjKey Then
            dict_pObjectKeys.Remove dict_i
            Exit Sub
        End If
    Next dict_i
End Sub

Private Function dict_GetKeyIndex(dict_Key As Variant) As Long
    Dim dict_i As Long
    For dict_i = 0 To UBound(dict_pKeys)
        If VBA.IsObject(dict_pKeys(dict_i)) And VBA.IsObject(dict_Key) Then
            If dict_pKeys(dict_i) Is dict_Key Then
                dict_GetKeyIndex = dict_i
                Exit For
            End If
        ElseIf VBA.IsObject(dict_pKeys(dict_i)) Or VBA.IsObject(dict_Key) Then
            ' Both need to be objects to check equality, skip
        ElseIf dict_pKeys(dict_i) = dict_Key Then
            dict_GetKeyIndex = dict_i
            Exit For
        End If
    Next dict_i
End Function

#End If

Private Sub Class_Initialize()
#If Mac Or Not UseScriptingDictionaryIfAvailable Then
    Set dict_pKeyValues = New Collection

    Erase dict_pKeys
    Erase dict_pItems
    Set dict_pObjectKeys = New Collection
#Else
    Set dict_pDictionary = CreateObject("Scripting.Dictionary")
#End If
End Sub

Private Sub Class_Terminate()
#If Mac Or Not UseScriptingDictionaryIfAvailable Then
    Set dict_pKeyValues = Nothing
    Set dict_pObjectKeys = Nothing
#Else
    Set dict_pDictionary = Nothing
#End If
End Sub

Attribute VB_Name = "Draw"
Sub Draw()

    Dim FSO As New FileSystemObject
    Dim JsonTS As TextStream
    Dim JsonText As String
    Dim Parsed As Dictionary
    Dim FileName As String
    Dim vba_var As String
    ThisDrawing.PurgeAll
    vba_var = ThisDrawing.GetVariable("users1")
        
        ThisDrawing.SetVariable "users1", ""
        
        'Using the SendCommand method, send getfiled AutoLISP expressions to the AutoCAD command line.
        'Set the return value to a user-defined system variable USERS1.
        ThisDrawing.SendCommand "(setvar " & """users1""" & "(getfiled " & """Select a GENESIS File""" & """""" & """genesis""" & "16)) "
        'Use the GetVariable method to retrieve this system variable to store the selected file name
        FileName = ThisDrawing.GetVariable("users1")
        If FileName <> "" Then
        
        ' Read .json file
        Set JsonTS = FSO.OpenTextFile(FileName, ForReading)
        JsonText = JsonTS.ReadAll
        JsonTS.Close
        JsonText = gen_decrypte(JsonText)
        
        ' Parse json to Dictionary
        Set Parsed = JsonConverter.ParseJson(JsonText)
        
    ' Set variables
    Dim face_id As Variant
    ReDim face_id(Parsed("ROOFS").Count + Parsed("OBSTRUCTIONS").Count)
    Dim roof As Variant
    Dim fId As Variant
    Dim I As LoadPictureConstants
    Dim rfblk As AcadBlockReference
    Dim arrstr() As Variant
        I = 0
        ' Step through each roof and grab face_id
        For Each roof In Parsed("ROOFS").Keys
            fId = Parsed("ROOFS")(roof)("FACE")
            face_id(I) = fId
            I = I + 1
            If Parsed("ROOFS")(roof)("DESIGNATION") <> Empty Then
                If TypeName(Parsed("ROOFS")(roof)("TAG_PT")) = "Collection" Then
                    If JsonConverter.ConvertToJson(Parsed("ROOFS")(roof)("TAG_PT")) <> "null" Then
                        Dim insertPt(0 To 2) As Double
                        insertPt(0) = CDbl(Parsed("ROOFS")(roof)("TAG_PT")(1))
                        insertPt(1) = CDbl(Parsed("ROOFS")(roof)("TAG_PT")(2))
                        insertPt(2) = CDbl(Parsed("ROOFS")(roof)("TAG_PT")(3))
                        rfname = "Roof" & CStr(Parsed("ROOFS")(roof)("DESIGNATION")) & "_ID"
                        Set rfblk = ThisDrawing.ModelSpace.InsertBlock(insertPt, rfname, 1, 1, 1, 0)
                        rfblk.Layer = "0"
                        ThisDrawing.SendCommand "(command " & """-layer""" & """Make""" & """N - ROOF NUMBERS""" & """""" & ") "
                        rfblk.Layer = "N - ROOF NUMBERS"
                        ReDim Preserve arrstr(I - 1)
                        arrstr(I - 1) = Parsed("ROOFS")(roof)("DESIGNATION")
                        'MsgBox (arrstr(i))
                        
                    End If
                    
                End If
                
            End If
            
        Next roof
        Dim newarrstr() As Variant
        Count = 0
        For Q = 0 To UBound(arrstr)
            If arrstr(Q) = Empty Then
                Count = Count + 1
            Else
                ReDim Preserve newarrstr(Q - Count)
                newarrstr(Q - Count) = arrstr(Q)
            End If
        Next Q
        
        maxrf = maxroof(newarrstr)
        ThisDrawing.SummaryInfo.SetCustomByKey "maxroof", CStr(maxrf)
        For Each obs In Parsed("OBSTRUCTIONS").Keys
            
                fId = Parsed("OBSTRUCTIONS")(obs)("FACE")
                face_id(I) = fId
                I = I + 1
            
        Next obs
        
    ' Set variables to grab line_ids
    Dim line_id As Variant
    ReDim line_id(Parsed("LINES").Count * 2)
    Dim face As Variant
    Dim lId As Variant
    Dim x As Long
    Dim b As Long
    
    b = 0
        ' Step through each face and grab line_id
        For Each face In Parsed("FACES").Keys
            x = 1
            ' If face is present in face_id array
            If IsInArray(face, face_id) Then
    
                ReDim lId(Parsed("FACES")(face)("LINES").Count)
                For Each ln In Parsed("FACES")(face)("LINES")
                    lId = Parsed("FACES")(face)("LINES")(x)
                    line_id(b) = lId
                    x = x + 1
                    b = b + 1
                Next ln
            End If
        Next face
    
    ' Set variables to grab pt_ids
    Dim pt_id As Variant
    ReDim pt_id(Parsed("FACES").Count)
    Dim lines As Variant
    Dim ptId As Variant
    Dim A As Long
    Dim roofLayer As AcadLayer
    Dim setbackLayer As AcadLayer
    Dim color As AcadAcCmColor
    Set color = AcadApplication.GetInterfaceObject("AutoCAD.AcCmColor." & Split(AcadApplication.Version, ".")(0))
    color.SetRGB 128, 128, 128
    
    ThisDrawing.SendCommand "(command " & """-layer""" & """Make""" & """R - ROOF LINES""" & """""" & ") "
    
        ' Step through each line to get pt_ids and coords
        For Each lines In Parsed("LINES").Keys
            A = 1
            Dim pt1(0 To 2) As Double
            Dim pt2(0 To 2) As Double
            Dim drawLine As AcadLine
            If IsInArray(lines, line_id) Then
                
                ReDim ptId(Parsed("LINES")(lines)("PTS").Count)
                For Each pt In Parsed("LINES")(lines)("PTS")
                    ptId = Parsed("LINES")(lines)("PTS")(A)
                    pt_id(A) = ptId
                    A = A + 1
                Next pt
                
                ' Set Coords to pt1 and pt2
                pt1(0) = Parsed("PTS")(pt_id(1))(1)
                pt1(1) = Parsed("PTS")(pt_id(1))(2)
                pt1(2) = Parsed("PTS")(pt_id(1))(3)
                pt2(0) = Parsed("PTS")(pt_id(2))(1)
                pt2(1) = Parsed("PTS")(pt_id(2))(2)
                pt2(2) = Parsed("PTS")(pt_id(2))(3)
                
                ' Draw Line
                Set drawLine = ThisDrawing.ModelSpace.AddLine(pt1, pt2)
                drawLine.Layer = "R - ROOF LINES"
                ZoomAll
            End If
        Next lines
        
    ThisDrawing.SendCommand "(command " & """-layer""" & """Make""" & """S - SETBACK LINES""" & """""" & ") "
    Set setbackLayer = ThisDrawing.Layers.Item("S - SETBACK LINES")
    setbackLayer.TrueColor = color
    
        If JsonConverter.ConvertToJson(Parsed("SETBACKS")) <> Empty Then
        If JsonConverter.ConvertToJson(Parsed("SETBACKS")("PTS")) <> Chr(34) & Chr(34) Then
            For Each pt In Parsed("SETBACKS")("PTS")
            
                Dim point1(0 To 2) As Double
                Dim point2(0 To 2) As Double
                Dim setbackLine As AcadLine
                
                point1(0) = pt(1)(1)
                point1(1) = pt(1)(2)
                point1(2) = pt(1)(3)
                point2(0) = pt(2)(1)
                point2(1) = pt(2)(2)
                point2(2) = pt(2)(3)
                
                Set setbackLine = ThisDrawing.ModelSpace.AddLine(point1, point2)
                setbackLine.Layer = "S - SETBACK LINES"
                ZoomAll
            
            Next pt
        End If
        End If
    
    Dim ctr_pt(0 To 2) As Double
    Dim mods As Variant
    Dim M As Variant
    Dim cPt_id As Variant
    Dim ct As Variant
    Dim c As Long
    Dim d As Long
    Dim blk As AcadBlockReference
    Dim insertFile As String
    Dim grab(0 To 2) As Double
    Dim tilt As Double
    Dim azim As Double
    Dim roofTilt As Double
    Dim roofAzim As Double
    Dim md As Variant
    Dim Y As Long
    Dim Pi As Double
    Dim modLayer As AcadLayer
    
    ThisDrawing.SendCommand "(command " & """-layer""" & """Make""" & """E - MODULE""" & """""" & ") "
    
    regularPanel = App_Path() & "genesis_module.dwg"
    microPanel = App_Path() & "micro_module.dwg"
    path1 = ThisDrawing.Path
    path2 = "\ACAD CALC TEMPLATE.xlsx"
    excelPath = path1 + path2
    
    Set xlapp = CreateObject("excel.application")

    xlapp.Workbooks.Open FileName:=excelPath

    xlapp.Visible = False
    
    If xlapp.Application.Cells(6, 6).Value <> "" Then
        insertFile = microPanel
    Else
        insertFile = regularPanel
    End If
    
    xlapp.DisplayAlerts = False

    xlapp.Application.ActiveWorkbook.SaveAs (excelPath)
    xlapp.Quit
    For Each roof In Parsed("ROOFS").Keys
        x = 0
        I = 1
        Y = 1
        Pi = 4 * Atn(1)
        
        If Parsed("ROOFS")(roof)("MODULES").Count > 0 Then
            Dim roofs As Variant
            ReDim roofs(0 To Parsed("ROOFS")(roof)("MODULES").Count - 1)
                For Each md In Parsed("ROOFS")(roof)("MODULES")
                    roofs(x) = Parsed("ROOFS")(roof)("MODULES")(Y)
                    x = x + 1
                    Y = Y + 1
                Next md
                
                tilt = Parsed("ROOFS")(roof)("TILT")
                azim = Parsed("ROOFS")(roof)("AZIMUTH")
                        
                ' Array of tilts and azimuths corresponding with roof numbers
                roofTilt = tilt * Pi / 180
                roofAzim = (180 - azim) * Pi / 180
                
                ' Step through each Module to get Center Points
                For Each mods In roofs
                c = 1
                d = 0
                
                    For Each ct In Parsed("MODULES")(mods)("CENTER_PT")
                        cPt_id = CDbl(Parsed("MODULES")(mods)("CENTER_PT")(c))
                        ctr_pt(d) = cPt_id
                        
                        c = c + 1
                        d = d + 1
                    Next ct
                    
                    If Parsed("MODULES")(mods)("ORIENTATION") = "port" Then
                        ' If orrientation is Portrait
                        grab(0) = ctr_pt(0) + 100
                        grab(1) = ctr_pt(1)
                        grab(2) = ctr_pt(2)
                        
                        Set blk = ThisDrawing.ModelSpace.InsertBlock(ctr_pt, insertFile, 1, 1, 1, 0)
                        blk.Rotate3D ctr_pt, grab, roofTilt
                        blk.Rotate ctr_pt, roofAzim
                        blk.Layer = "E - MODULE"
                    ElseIf Parsed("MODULES")(mods)("ORIENTATION") = "land" Then
                        roofAzimLand = -90 * Pi / 180
                        grab(0) = ctr_pt(0)
                        grab(1) = ctr_pt(1) + 100
                        grab(2) = ctr_pt(2)
                        
                        Set blk = ThisDrawing.ModelSpace.InsertBlock(ctr_pt, insertFile, 1, 1, 1, 0)
                        blk.Rotate3D ctr_pt, grab, roofTilt
                        blk.Rotate ctr_pt, roofAzim + roofAzimLand
                        blk.Layer = "E - MODULE"
                    End If
                Next mods
                currentroof = Parsed("ROOFS")(roof)("DESIGNATION")
                currentpitch = Parsed("ROOFS")(roof)("TILT")
                currentorientation = Parsed("ROOFS")(roof)("AZIMUTH")
                ThisDrawing.SummaryInfo.SetCustomByKey "currRoof", currentroof
                ThisDrawing.SummaryInfo.SetCustomByKey "currpitch", currentpitch
                ThisDrawing.SummaryInfo.SetCustomByKey "currorientation", currentorientation
                ThisDrawing.SendCommand ("QB" & vbCr)
            End If
        Next roof
        
        End If
        ThisDrawing.SendCommand ("RFTXT" & vbCr)
        ThisDrawing.SendCommand ("modcount" & vbCr)
        ThisDrawing.Regen acActiveViewport
        ThisDrawing.SetVariable "users1", ""
        
End Sub

Function IsInArray(str As Variant, arr As Variant) As Boolean
    Dim I
    For I = LBound(arr) To UBound(arr)
        If arr(I) = str Then
            IsInArray = True
            Exit Function
        End If
    Next I
    IsInArray = False

End Function
Public Function App_Path() As String
   Dim str As String
   str = ThisDrawing.Application.VBE.ActiveVBProject.FileName
   App_Path = GetPathFromFilename(str)
End Function

Public Function GetPathFromFilename(sFile) As String
   Dim arr() As String
   arr = Split(sFile, "\", -1, vbTextCompare)
   GetPathFromFilename = Left(sFile, Len(sFile) - Len(arr(UBound(arr))))
End Function
Function gen_decrypte(str) As String
    Dim chars As String
    Dim syms As String
    chars = "ABCDEFGHIJKLMNOPQRSTUVWXYZabcdefghijklmnopqrstuvwxyz1234567890!@#$%^&*()_-+={}[]|:;'<>,.?/ "
    syms = "@F_3y4X%eBjxVU{5<(,RdKf#=IPDJLA9'} Ho[|iThrN^ngv+sSWE*C6m)t-b?O2]qk8z>:Qwc0!Y;&la7uMp1$.Z/G"
    Dim symbols() As String
    ReDim symbols(Len(chars) - 1)
    Dim enc_symbols() As String
    ReDim enc_symbols(Len(syms) - 1)
    Dim str_arr() As String
    ReDim str_arr(Len(str) - 1)
    Dim hash As Dictionary
    Dim char As String
    Dim new_char As String
    Dim new_str As String
    Dim I As Long
    Set hash = New Dictionary
    
    For I = 1 To Len(chars)
        symbols(I - 1) = Mid$(chars, I, 1)
    Next
     
    For I = 1 To Len(syms)
        enc_symbols(I - 1) = Mid$(syms, I, 1)
    Next
    
    I = 0
    For Each c In enc_symbols
        hash.Add enc_symbols(I), symbols(I)
        I = I + 1
    Next c
    
    new_str = Space(Len(str))
    I = 1
    Do While I < Len(str) + 1
        char = Mid$(str, I, 1)
        new_char = hash(char)
        If new_char <> "" Then
            Mid$(new_str, I, 1) = new_char
        Else
            Mid$(new_str, I, 1) = char
        End If
        I = I + 1
    Loop
    
    gen_decrypte = new_str
End Function
Public Function maxroof(arr)

k = 0
For Each j In arr
    If k < j Then
        k = j
    Else
        k = k
    End If
Next j

maxroof = k

End Function

Attribute VB_Name = "JsonConverter"
''
' VBA-JSON v2.2.3
' (c) Tim Hall - https://github.com/VBA-tools/VBA-JSON
'
' JSON Converter for VBA
'
' Errors:
' 10001 - JSON parse error
'
' @class JsonConverter
' @author tim.hall.engr@gmail.com
' @license MIT (http://www.opensource.org/licenses/mit-license.php)
'' ~~~~~~~~~~~~~~~~~~~~~~~~~~~~~~~~~~~~~~~~~~~~~~~~~~~~~~~~~~~~~~~~~~~~~~ '
'
' Based originally on vba-json (with extensive changes)
' BSD license included below
'
' JSONLib, http://code.google.com/p/vba-json/
'
' Copyright (c) 2013, Ryo Yokoyama
' All rights reserved.
'
' Redistribution and use in source and binary forms, with or without
' modification, are permitted provided that the following conditions are met:
'     * Redistributions of source code must retain the above copyright
'       notice, this list of conditions and the following disclaimer.
'     * Redistributions in binary form must reproduce the above copyright
'       notice, this list of conditions and the following disclaimer in the
'       documentation and/or other materials provided with the distribution.
'     * Neither the name of the <organization> nor the
'       names of its contributors may be used to endorse or promote products
'       derived from this software without specific prior written permission.
'
' THIS SOFTWARE IS PROVIDED BY THE COPYRIGHT HOLDERS AND CONTRIBUTORS "AS IS" AND
' ANY EXPRESS OR IMPLIED WARRANTIES, INCLUDING, BUT NOT LIMITED TO, THE IMPLIED
' WARRANTIES OF MERCHANTABILITY AND FITNESS FOR A PARTICULAR PURPOSE ARE
' DISCLAIMED. IN NO EVENT SHALL <COPYRIGHT HOLDER> BE LIABLE FOR ANY
' DIRECT, INDIRECT, INCIDENTAL, SPECIAL, EXEMPLARY, OR CONSEQUENTIAL DAMAGES
' (INCLUDING, BUT NOT LIMITED TO, PROCUREMENT OF SUBSTITUTE GOODS OR SERVICES;
' LOSS OF USE, DATA, OR PROFITS; OR BUSINESS INTERRUPTION) HOWEVER CAUSED AND
' ON ANY THEORY OF LIABILITY, WHETHER IN CONTRACT, STRICT LIABILITY, OR TORT
' (INCLUDING NEGLIGENCE OR OTHERWISE) ARISING IN ANY WAY OUT OF THE USE OF THIS
' SOFTWARE, EVEN IF ADVISED OF THE POSSIBILITY OF SUCH DAMAGE.
' ~~~~~~~~~~~~~~~~~~~~~~~~~~~~~~~~~~~~~~~~~~~~~~~~~~~~~~~~~~~~~~~~~~~~~~ '
Option Explicit

' === VBA-UTC Headers
#If Mac Then

#If VBA7 Then

' 64-bit Mac (2016)
Private Declare PtrSafe Function utc_popen Lib "libc.dylib" Alias "popen" _
    (ByVal utc_Command As String, ByVal utc_Mode As String) As LongPtr
Private Declare PtrSafe Function utc_pclose Lib "libc.dylib" Alias "pclose" _
    (ByVal utc_File As Long) As LongPtr
Private Declare PtrSafe Function utc_fread Lib "libc.dylib" Alias "fread" _
    (ByVal utc_Buffer As String, ByVal utc_Size As LongPtr, ByVal utc_Number As LongPtr, ByVal utc_File As LongPtr) As LongPtr
Private Declare PtrSafe Function utc_feof Lib "libc.dylib" Alias "feof" _
    (ByVal utc_File As LongPtr) As LongPtr

#Else

' 32-bit Mac
Private Declare Function utc_popen Lib "libc.dylib" Alias "popen" _
    (ByVal utc_Command As String, ByVal utc_Mode As String) As Long
Private Declare Function utc_pclose Lib "libc.dylib" Alias "pclose" _
    (ByVal utc_File As Long) As Long
Private Declare Function utc_fread Lib "libc.dylib" Alias "fread" _
    (ByVal utc_Buffer As String, ByVal utc_Size As Long, ByVal utc_Number As Long, ByVal utc_File As Long) As Long
Private Declare Function utc_feof Lib "libc.dylib" Alias "feof" _
    (ByVal utc_File As Long) As Long

#End If

#ElseIf VBA7 Then

' http://msdn.microsoft.com/en-us/library/windows/desktop/ms724421.aspx
' http://msdn.microsoft.com/en-us/library/windows/desktop/ms724949.aspx
' http://msdn.microsoft.com/en-us/library/windows/desktop/ms725485.aspx
Private Declare PtrSafe Function utc_GetTimeZoneInformation Lib "kernel32" Alias "GetTimeZoneInformation" _
    (utc_lpTimeZoneInformation As utc_TIME_ZONE_INFORMATION) As Long
Private Declare PtrSafe Function utc_SystemTimeToTzSpecificLocalTime Lib "kernel32" Alias "SystemTimeToTzSpecificLocalTime" _
    (utc_lpTimeZoneInformation As utc_TIME_ZONE_INFORMATION, utc_lpUniversalTime As utc_SYSTEMTIME, utc_lpLocalTime As utc_SYSTEMTIME) As Long
Private Declare PtrSafe Function utc_TzSpecificLocalTimeToSystemTime Lib "kernel32" Alias "TzSpecificLocalTimeToSystemTime" _
    (utc_lpTimeZoneInformation As utc_TIME_ZONE_INFORMATION, utc_lpLocalTime As utc_SYSTEMTIME, utc_lpUniversalTime As utc_SYSTEMTIME) As Long

#Else

Private Declare Function utc_GetTimeZoneInformation Lib "kernel32" Alias "GetTimeZoneInformation" _
    (utc_lpTimeZoneInformation As utc_TIME_ZONE_INFORMATION) As Long
Private Declare Function utc_SystemTimeToTzSpecificLocalTime Lib "kernel32" Alias "SystemTimeToTzSpecificLocalTime" _
    (utc_lpTimeZoneInformation As utc_TIME_ZONE_INFORMATION, utc_lpUniversalTime As utc_SYSTEMTIME, utc_lpLocalTime As utc_SYSTEMTIME) As Long
Private Declare Function utc_TzSpecificLocalTimeToSystemTime Lib "kernel32" Alias "TzSpecificLocalTimeToSystemTime" _
    (utc_lpTimeZoneInformation As utc_TIME_ZONE_INFORMATION, utc_lpLocalTime As utc_SYSTEMTIME, utc_lpUniversalTime As utc_SYSTEMTIME) As Long

#End If

#If Mac Then

#If VBA7 Then
Private Type utc_ShellResult
    utc_Output As String
    utc_ExitCode As LongPtr
End Type

#Else

Private Type utc_ShellResult
    utc_Output As String
    utc_ExitCode As Long
End Type

#End If

#Else

Private Type utc_SYSTEMTIME
    utc_wYear As Integer
    utc_wMonth As Integer
    utc_wDayOfWeek As Integer
    utc_wDay As Integer
    utc_wHour As Integer
    utc_wMinute As Integer
    utc_wSecond As Integer
    utc_wMilliseconds As Integer
End Type

Private Type utc_TIME_ZONE_INFORMATION
    utc_Bias As Long
    utc_StandardName(0 To 31) As Integer
    utc_StandardDate As utc_SYSTEMTIME
    utc_StandardBias As Long
    utc_DaylightName(0 To 31) As Integer
    utc_DaylightDate As utc_SYSTEMTIME
    utc_DaylightBias As Long
End Type

#End If
' === End VBA-UTC

#If Mac Then
#ElseIf VBA7 Then

Private Declare PtrSafe Sub json_CopyMemory Lib "kernel32" Alias "RtlMoveMemory" _
    (json_MemoryDestination As Any, json_MemorySource As Any, ByVal json_ByteLength As Long)

#Else

Private Declare Sub json_CopyMemory Lib "kernel32" Alias "RtlMoveMemory" _
    (json_MemoryDestination As Any, json_MemorySource As Any, ByVal json_ByteLength As Long)

#End If

Private Type json_Options
    ' VBA only stores 15 significant digits, so any numbers larger than that are truncated
    ' This can lead to issues when BIGINT's are used (e.g. for Ids or Credit Cards), as they will be invalid above 15 digits
    ' See: http://support.microsoft.com/kb/269370
    '
    ' By default, VBA-JSON will use String for numbers longer than 15 characters that contain only digits
    ' to override set `JsonConverter.JsonOptions.UseDoubleForLargeNumbers = True`
    UseDoubleForLargeNumbers As Boolean

    ' The JSON standard requires object keys to be quoted (" or '), use this option to allow unquoted keys
    AllowUnquotedKeys As Boolean

    ' The solidus (/) is not required to be escaped, use this option to escape them as \/ in ConvertToJson
    EscapeSolidus As Boolean
End Type
Public JsonOptions As json_Options

' ============================================= '
' Public Methods
' ============================================= '

''
' Convert JSON string to object (Dictionary/Collection)
'
' @method ParseJson
' @param {String} json_String
' @return {Object} (Dictionary or Collection)
' @throws 10001 - JSON parse error
''
Public Function ParseJson(ByVal JsonString As String) As Object
    Dim json_Index As Long
    json_Index = 1

    ' Remove vbCr, vbLf, and vbTab from json_String
    JsonString = VBA.Replace(VBA.Replace(VBA.Replace(JsonString, VBA.vbCr, ""), VBA.vbLf, ""), VBA.vbTab, "")

    json_SkipSpaces JsonString, json_Index
    Select Case VBA.Mid$(JsonString, json_Index, 1)
    Case "{"
        Set ParseJson = json_ParseObject(JsonString, json_Index)
    Case "["
        Set ParseJson = json_ParseArray(JsonString, json_Index)
    Case Else
        ' Error: Invalid JSON string
        Err.Raise 10001, "JSONConverter", json_ParseErrorMessage(JsonString, json_Index, "Expecting '{' or '['")
    End Select
End Function

''
' Convert object (Dictionary/Collection/Array) to JSON
'
' @method ConvertToJson
' @param {Variant} JsonValue (Dictionary, Collection, or Array)
' @param {Integer|String} Whitespace "Pretty" print json with given number of spaces per indentation (Integer) or given string
' @return {String}
''
Public Function ConvertToJson(ByVal JsonValue As Variant, Optional ByVal Whitespace As Variant, Optional ByVal json_CurrentIndentation As Long = 0) As String
    Dim json_buffer As String
    Dim json_BufferPosition As Long
    Dim json_BufferLength As Long
    Dim json_Index As Long
    Dim json_LBound As Long
    Dim json_UBound As Long
    Dim json_IsFirstItem As Boolean
    Dim json_Index2D As Long
    Dim json_LBound2D As Long
    Dim json_UBound2D As Long
    Dim json_IsFirstItem2D As Boolean
    Dim json_Key As Variant
    Dim json_Value As Variant
    Dim json_DateStr As String
    Dim json_Converted As String
    Dim json_SkipItem As Boolean
    Dim json_PrettyPrint As Boolean
    Dim json_Indentation As String
    Dim json_InnerIndentation As String

    json_LBound = -1
    json_UBound = -1
    json_IsFirstItem = True
    json_LBound2D = -1
    json_UBound2D = -1
    json_IsFirstItem2D = True
    json_PrettyPrint = Not IsMissing(Whitespace)

    Select Case VBA.VarType(JsonValue)
    Case VBA.vbNull
        ConvertToJson = "null"
    Case VBA.vbDate
        ' Date
        json_DateStr = ConvertToIso(VBA.CDate(JsonValue))

        ConvertToJson = """" & json_DateStr & """"
    Case VBA.vbString
        ' String (or large number encoded as string)
        If Not JsonOptions.UseDoubleForLargeNumbers And json_StringIsLargeNumber(JsonValue) Then
            ConvertToJson = JsonValue
        Else
            ConvertToJson = """" & json_Encode(JsonValue) & """"
        End If
    Case VBA.vbBoolean
        If JsonValue Then
            ConvertToJson = "true"
        Else
            ConvertToJson = "false"
        End If
    Case VBA.vbArray To VBA.vbArray + VBA.vbByte
        If json_PrettyPrint Then
            If VBA.VarType(Whitespace) = VBA.vbString Then
                json_Indentation = VBA.String$(json_CurrentIndentation + 1, Whitespace)
                json_InnerIndentation = VBA.String$(json_CurrentIndentation + 2, Whitespace)
            Else
                json_Indentation = VBA.Space$((json_CurrentIndentation + 1) * Whitespace)
                json_InnerIndentation = VBA.Space$((json_CurrentIndentation + 2) * Whitespace)
            End If
        End If

        ' Array
        json_BufferAppend json_buffer, "[", json_BufferPosition, json_BufferLength

        On Error Resume Next

        json_LBound = LBound(JsonValue, 1)
        json_UBound = UBound(JsonValue, 1)
        json_LBound2D = LBound(JsonValue, 2)
        json_UBound2D = UBound(JsonValue, 2)

        If json_LBound >= 0 And json_UBound >= 0 Then
            For json_Index = json_LBound To json_UBound
                If json_IsFirstItem Then
                    json_IsFirstItem = False
                Else
                    ' Append comma to previous line
                    json_BufferAppend json_buffer, ",", json_BufferPosition, json_BufferLength
                End If

                If json_LBound2D >= 0 And json_UBound2D >= 0 Then
                    ' 2D Array
                    If json_PrettyPrint Then
                        json_BufferAppend json_buffer, vbNewLine, json_BufferPosition, json_BufferLength
                    End If
                    json_BufferAppend json_buffer, json_Indentation & "[", json_BufferPosition, json_BufferLength

                    For json_Index2D = json_LBound2D To json_UBound2D
                        If json_IsFirstItem2D Then
                            json_IsFirstItem2D = False
                        Else
                            json_BufferAppend json_buffer, ",", json_BufferPosition, json_BufferLength
                        End If

                        json_Converted = ConvertToJson(JsonValue(json_Index, json_Index2D), Whitespace, json_CurrentIndentation + 2)

                        ' For Arrays/Collections, undefined (Empty/Nothing) is treated as null
                        If json_Converted = "" Then
                            ' (nest to only check if converted = "")
                            If json_IsUndefined(JsonValue(json_Index, json_Index2D)) Then
                                json_Converted = "null"
                            End If
                        End If

                        If json_PrettyPrint Then
                            json_Converted = vbNewLine & json_InnerIndentation & json_Converted
                        End If

                        json_BufferAppend json_buffer, json_Converted, json_BufferPosition, json_BufferLength
                    Next json_Index2D

                    If json_PrettyPrint Then
                        json_BufferAppend json_buffer, vbNewLine, json_BufferPosition, json_BufferLength
                    End If

                    json_BufferAppend json_buffer, json_Indentation & "]", json_BufferPosition, json_BufferLength
                    json_IsFirstItem2D = True
                Else
                    ' 1D Array
                    json_Converted = ConvertToJson(JsonValue(json_Index), Whitespace, json_CurrentIndentation + 1)

                    ' For Arrays/Collections, undefined (Empty/Nothing) is treated as null
                    If json_Converted = "" Then
                        ' (nest to only check if converted = "")
                        If json_IsUndefined(JsonValue(json_Index)) Then
                            json_Converted = "null"
                        End If
                    End If

                    If json_PrettyPrint Then
                        json_Converted = vbNewLine & json_Indentation & json_Converted
                    End If

                    json_BufferAppend json_buffer, json_Converted, json_BufferPosition, json_BufferLength
                End If
            Next json_Index
        End If

        On Error GoTo 0

        If json_PrettyPrint Then
            json_BufferAppend json_buffer, vbNewLine, json_BufferPosition, json_BufferLength

            If VBA.VarType(Whitespace) = VBA.vbString Then
                json_Indentation = VBA.String$(json_CurrentIndentation, Whitespace)
            Else
                json_Indentation = VBA.Space$(json_CurrentIndentation * Whitespace)
            End If
        End If

        json_BufferAppend json_buffer, json_Indentation & "]", json_BufferPosition, json_BufferLength

        ConvertToJson = json_BufferToString(json_buffer, json_BufferPosition, json_BufferLength)

    ' Dictionary or Collection
    Case VBA.vbObject
        If json_PrettyPrint Then
            If VBA.VarType(Whitespace) = VBA.vbString Then
                json_Indentation = VBA.String$(json_CurrentIndentation + 1, Whitespace)
            Else
                json_Indentation = VBA.Space$((json_CurrentIndentation + 1) * Whitespace)
            End If
        End If

        ' Dictionary
        If VBA.TypeName(JsonValue) = "Dictionary" Then
            json_BufferAppend json_buffer, "{", json_BufferPosition, json_BufferLength
            For Each json_Key In JsonValue.Keys
                ' For Objects, undefined (Empty/Nothing) is not added to object
                json_Converted = ConvertToJson(JsonValue(json_Key), Whitespace, json_CurrentIndentation + 1)
                If json_Converted = "" Then
                    json_SkipItem = json_IsUndefined(JsonValue(json_Key))
                Else
                    json_SkipItem = False
                End If

                If Not json_SkipItem Then
                    If json_IsFirstItem Then
                        json_IsFirstItem = False
                    Else
                        json_BufferAppend json_buffer, ",", json_BufferPosition, json_BufferLength
                    End If

                    If json_PrettyPrint Then
                        json_Converted = vbNewLine & json_Indentation & """" & json_Key & """: " & json_Converted
                    Else
                        json_Converted = """" & json_Key & """:" & json_Converted
                    End If

                    json_BufferAppend json_buffer, json_Converted, json_BufferPosition, json_BufferLength
                End If
            Next json_Key

            If json_PrettyPrint Then
                json_BufferAppend json_buffer, vbNewLine, json_BufferPosition, json_BufferLength

                If VBA.VarType(Whitespace) = VBA.vbString Then
                    json_Indentation = VBA.String$(json_CurrentIndentation, Whitespace)
                Else
                    json_Indentation = VBA.Space$(json_CurrentIndentation * Whitespace)
                End If
            End If

            json_BufferAppend json_buffer, json_Indentation & "}", json_BufferPosition, json_BufferLength

        ' Collection
        ElseIf VBA.TypeName(JsonValue) = "Collection" Then
            json_BufferAppend json_buffer, "[", json_BufferPosition, json_BufferLength
            For Each json_Value In JsonValue
                If json_IsFirstItem Then
                    json_IsFirstItem = False
                Else
                    json_BufferAppend json_buffer, ",", json_BufferPosition, json_BufferLength
                End If

                json_Converted = ConvertToJson(json_Value, Whitespace, json_CurrentIndentation + 1)

                ' For Arrays/Collections, undefined (Empty/Nothing) is treated as null
                If json_Converted = "" Then
                    ' (nest to only check if converted = "")
                    If json_IsUndefined(json_Value) Then
                        json_Converted = "null"
                    End If
                End If

                If json_PrettyPrint Then
                    json_Converted = vbNewLine & json_Indentation & json_Converted
                End If

                json_BufferAppend json_buffer, json_Converted, json_BufferPosition, json_BufferLength
            Next json_Value

            If json_PrettyPrint Then
                json_BufferAppend json_buffer, vbNewLine, json_BufferPosition, json_BufferLength

                If VBA.VarType(Whitespace) = VBA.vbString Then
                    json_Indentation = VBA.String$(json_CurrentIndentation, Whitespace)
                Else
                    json_Indentation = VBA.Space$(json_CurrentIndentation * Whitespace)
                End If
            End If

            json_BufferAppend json_buffer, json_Indentation & "]", json_BufferPosition, json_BufferLength
        End If

        ConvertToJson = json_BufferToString(json_buffer, json_BufferPosition, json_BufferLength)
    Case VBA.vbInteger, VBA.vbLong, VBA.vbSingle, VBA.vbDouble, VBA.vbCurrency, VBA.vbDecimal
        ' Number (use decimals for numbers)
        ConvertToJson = VBA.Replace(JsonValue, ",", ".")
    Case Else
        ' vbEmpty, vbError, vbDataObject, vbByte, vbUserDefinedType
        ' Use VBA's built-in to-string
        On Error Resume Next
        ConvertToJson = JsonValue
        On Error GoTo 0
    End Select
End Function

' ============================================= '
' Private Functions
' ============================================= '

Private Function json_ParseObject(json_String As String, ByRef json_Index As Long) As Dictionary
    Dim json_Key As String
    Dim json_NextChar As String

    Set json_ParseObject = New Dictionary
    json_SkipSpaces json_String, json_Index
    If VBA.Mid$(json_String, json_Index, 1) <> "{" Then
        Err.Raise 10001, "JSONConverter", json_ParseErrorMessage(json_String, json_Index, "Expecting '{'")
    Else
        json_Index = json_Index + 1

        Do
            json_SkipSpaces json_String, json_Index
            If VBA.Mid$(json_String, json_Index, 1) = "}" Then
                json_Index = json_Index + 1
                Exit Function
            ElseIf VBA.Mid$(json_String, json_Index, 1) = "," Then
                json_Index = json_Index + 1
                json_SkipSpaces json_String, json_Index
            End If

            json_Key = json_ParseKey(json_String, json_Index)
            json_NextChar = json_Peek(json_String, json_Index)
            If json_NextChar = "[" Or json_NextChar = "{" Then
                Set json_ParseObject.Item(json_Key) = json_ParseValue(json_String, json_Index)
            Else
                json_ParseObject.Item(json_Key) = json_ParseValue(json_String, json_Index)
            End If
        Loop
    End If
End Function

Private Function json_ParseArray(json_String As String, ByRef json_Index As Long) As Collection
    Set json_ParseArray = New Collection

    json_SkipSpaces json_String, json_Index
    If VBA.Mid$(json_String, json_Index, 1) <> "[" Then
        Err.Raise 10001, "JSONConverter", json_ParseErrorMessage(json_String, json_Index, "Expecting '['")
    Else
        json_Index = json_Index + 1

        Do
            json_SkipSpaces json_String, json_Index
            If VBA.Mid$(json_String, json_Index, 1) = "]" Then
                json_Index = json_Index + 1
                Exit Function
            ElseIf VBA.Mid$(json_String, json_Index, 1) = "," Then
                json_Index = json_Index + 1
                json_SkipSpaces json_String, json_Index
            End If

            json_ParseArray.Add json_ParseValue(json_String, json_Index)
        Loop
    End If
End Function

Private Function json_ParseValue(json_String As String, ByRef json_Index As Long) As Variant
    json_SkipSpaces json_String, json_Index
    Select Case VBA.Mid$(json_String, json_Index, 1)
    Case "{"
        Set json_ParseValue = json_ParseObject(json_String, json_Index)
    Case "["
        Set json_ParseValue = json_ParseArray(json_String, json_Index)
    Case """", "'"
        json_ParseValue = json_ParseString(json_String, json_Index)
    Case Else
        If VBA.Mid$(json_String, json_Index, 4) = "true" Then
            json_ParseValue = True
            json_Index = json_Index + 4
        ElseIf VBA.Mid$(json_String, json_Index, 5) = "false" Then
            json_ParseValue = False
            json_Index = json_Index + 5
        ElseIf VBA.Mid$(json_String, json_Index, 4) = "null" Then
            json_ParseValue = Null
            json_Index = json_Index + 4
        ElseIf VBA.InStr("+-0123456789", VBA.Mid$(json_String, json_Index, 1)) Then
            json_ParseValue = json_ParseNumber(json_String, json_Index)
        Else
            Err.Raise 10001, "JSONConverter", json_ParseErrorMessage(json_String, json_Index, "Expecting 'STRING', 'NUMBER', null, true, false, '{', or '['")
        End If
    End Select
End Function

Private Function json_ParseString(json_String As String, ByRef json_Index As Long) As String
    Dim json_Quote As String
    Dim json_Char As String
    Dim json_Code As String
    Dim json_buffer As String
    Dim json_BufferPosition As Long
    Dim json_BufferLength As Long

    json_SkipSpaces json_String, json_Index

    ' Store opening quote to look for matching closing quote
    json_Quote = VBA.Mid$(json_String, json_Index, 1)
    json_Index = json_Index + 1

    Do While json_Index > 0 And json_Index <= Len(json_String)
        json_Char = VBA.Mid$(json_String, json_Index, 1)

        Select Case json_Char
        Case "\"
            ' Escaped string, \\, or \/
            json_Index = json_Index + 1
            json_Char = VBA.Mid$(json_String, json_Index, 1)

            Select Case json_Char
            Case """", "\", "/", "'"
                json_BufferAppend json_buffer, json_Char, json_BufferPosition, json_BufferLength
                json_Index = json_Index + 1
            Case "b"
                json_BufferAppend json_buffer, vbBack, json_BufferPosition, json_BufferLength
                json_Index = json_Index + 1
            Case "f"
                json_BufferAppend json_buffer, vbFormFeed, json_BufferPosition, json_BufferLength
                json_Index = json_Index + 1
            Case "n"
                json_BufferAppend json_buffer, vbCrLf, json_BufferPosition, json_BufferLength
                json_Index = json_Index + 1
            Case "r"
                json_BufferAppend json_buffer, vbCr, json_BufferPosition, json_BufferLength
                json_Index = json_Index + 1
            Case "t"
                json_BufferAppend json_buffer, vbTab, json_BufferPosition, json_BufferLength
                json_Index = json_Index + 1
            Case "u"
                ' Unicode character escape (e.g. \u00a9 = Copyright)
                json_Index = json_Index + 1
                json_Code = VBA.Mid$(json_String, json_Index, 4)
                json_BufferAppend json_buffer, VBA.ChrW(VBA.Val("&h" + json_Code)), json_BufferPosition, json_BufferLength
                json_Index = json_Index + 4
            End Select
        Case json_Quote
            json_ParseString = json_BufferToString(json_buffer, json_BufferPosition, json_BufferLength)
            json_Index = json_Index + 1
            Exit Function
        Case Else
            json_BufferAppend json_buffer, json_Char, json_BufferPosition, json_BufferLength
            json_Index = json_Index + 1
        End Select
    Loop
End Function

Private Function json_ParseNumber(json_String As String, ByRef json_Index As Long) As Variant
    Dim json_Char As String
    Dim json_Value As String
    Dim json_IsLargeNumber As Boolean

    json_SkipSpaces json_String, json_Index

    Do While json_Index > 0 And json_Index <= Len(json_String)
        json_Char = VBA.Mid$(json_String, json_Index, 1)

        If VBA.InStr("+-0123456789.eE", json_Char) Then
            ' Unlikely to have massive number, so use simple append rather than buffer here
            json_Value = json_Value & json_Char
            json_Index = json_Index + 1
        Else
            ' Excel only stores 15 significant digits, so any numbers larger than that are truncated
            ' This can lead to issues when BIGINT's are used (e.g. for Ids or Credit Cards), as they will be invalid above 15 digits
            ' See: http://support.microsoft.com/kb/269370
            '
            ' Fix: Parse -> String, Convert -> String longer than 15/16 characters containing only numbers and decimal points -> Number
            ' (decimal doesn't factor into significant digit count, so if present check for 15 digits + decimal = 16)
            json_IsLargeNumber = IIf(InStr(json_Value, "."), Len(json_Value) >= 17, Len(json_Value) >= 16)
            If Not JsonOptions.UseDoubleForLargeNumbers And json_IsLargeNumber Then
                json_ParseNumber = json_Value
            Else
                ' VBA.Val does not use regional settings, so guard for comma is not needed
                json_ParseNumber = VBA.Val(json_Value)
            End If
            Exit Function
        End If
    Loop
End Function

Private Function json_ParseKey(json_String As String, ByRef json_Index As Long) As String
    ' Parse key with single or double quotes
    If VBA.Mid$(json_String, json_Index, 1) = """" Or VBA.Mid$(json_String, json_Index, 1) = "'" Then
        json_ParseKey = json_ParseString(json_String, json_Index)
    ElseIf JsonOptions.AllowUnquotedKeys Then
        Dim json_Char As String
        Do While json_Index > 0 And json_Index <= Len(json_String)
            json_Char = VBA.Mid$(json_String, json_Index, 1)
            If (json_Char <> " ") And (json_Char <> ":") Then
                json_ParseKey = json_ParseKey & json_Char
                json_Index = json_Index + 1
            Else
                Exit Do
            End If
        Loop
    Else
        Err.Raise 10001, "JSONConverter", json_ParseErrorMessage(json_String, json_Index, "Expecting '""' or '''")
    End If

    ' Check for colon and skip if present or throw if not present
    json_SkipSpaces json_String, json_Index
    If VBA.Mid$(json_String, json_Index, 1) <> ":" Then
        Err.Raise 10001, "JSONConverter", json_ParseErrorMessage(json_String, json_Index, "Expecting ':'")
    Else
        json_Index = json_Index + 1
    End If
End Function

Private Function json_IsUndefined(ByVal json_Value As Variant) As Boolean
    ' Empty / Nothing -> undefined
    Select Case VBA.VarType(json_Value)
    Case VBA.vbEmpty
        json_IsUndefined = True
    Case VBA.vbObject
        Select Case VBA.TypeName(json_Value)
        Case "Empty", "Nothing"
            json_IsUndefined = True
        End Select
    End Select
End Function

Private Function json_Encode(ByVal json_Text As Variant) As String
    ' Reference: http://www.ietf.org/rfc/rfc4627.txt
    ' Escape: ", \, /, backspace, form feed, line feed, carriage return, tab
    Dim json_Index As Long
    Dim json_Char As String
    Dim json_AscCode As Long
    Dim json_buffer As String
    Dim json_BufferPosition As Long
    Dim json_BufferLength As Long

    For json_Index = 1 To VBA.Len(json_Text)
        json_Char = VBA.Mid$(json_Text, json_Index, 1)
        json_AscCode = VBA.AscW(json_Char)

        ' When AscW returns a negative number, it returns the twos complement form of that number.
        ' To convert the twos complement notation into normal binary notation, add 0xFFF to the return result.
        ' https://support.microsoft.com/en-us/kb/272138
        If json_AscCode < 0 Then
            json_AscCode = json_AscCode + 65536
        End If

        ' From spec, ", \, and control characters must be escaped (solidus is optional)

        Select Case json_AscCode
        Case 34
            ' " -> 34 -> \"
            json_Char = "\"""
        Case 92
            ' \ -> 92 -> \\
            json_Char = "\\"
        Case 47
            ' / -> 47 -> \/ (optional)
            If JsonOptions.EscapeSolidus Then
                json_Char = "\/"
            End If
        Case 8
            ' backspace -> 8 -> \b
            json_Char = "\b"
        Case 12
            ' form feed -> 12 -> \f
            json_Char = "\f"
        Case 10
            ' line feed -> 10 -> \n
            json_Char = "\n"
        Case 13
            ' carriage return -> 13 -> \r
            json_Char = "\r"
        Case 9
            ' tab -> 9 -> \t
            json_Char = "\t"
        Case 0 To 31, 127 To 65535
            ' Non-ascii characters -> convert to 4-digit hex
            json_Char = "\u" & VBA.Right$("0000" & VBA.Hex$(json_AscCode), 4)
        End Select

        json_BufferAppend json_buffer, json_Char, json_BufferPosition, json_BufferLength
    Next json_Index

    json_Encode = json_BufferToString(json_buffer, json_BufferPosition, json_BufferLength)
End Function

Private Function json_Peek(json_String As String, ByVal json_Index As Long, Optional json_NumberOfCharacters As Long = 1) As String
    ' "Peek" at the next number of characters without incrementing json_Index (ByVal instead of ByRef)
    json_SkipSpaces json_String, json_Index
    json_Peek = VBA.Mid$(json_String, json_Index, json_NumberOfCharacters)
End Function

Private Sub json_SkipSpaces(json_String As String, ByRef json_Index As Long)
    ' Increment index to skip over spaces
    Do While json_Index > 0 And json_Index <= VBA.Len(json_String) And VBA.Mid$(json_String, json_Index, 1) = " "
        json_Index = json_Index + 1
    Loop
End Sub

Private Function json_StringIsLargeNumber(json_String As Variant) As Boolean
    ' Check if the given string is considered a "large number"
    ' (See json_ParseNumber)

    Dim json_Length As Long
    Dim json_CharIndex As Long
    json_Length = VBA.Len(json_String)

    ' Length with be at least 16 characters and assume will be less than 100 characters
    If json_Length >= 16 And json_Length <= 100 Then
        Dim json_CharCode As String
        Dim json_Index As Long

        json_StringIsLargeNumber = True

        For json_CharIndex = 1 To json_Length
            json_CharCode = VBA.Asc(VBA.Mid$(json_String, json_CharIndex, 1))
            Select Case json_CharCode
            ' Look for .|0-9|E|e
            Case 46, 48 To 57, 69, 101
                ' Continue through characters
            Case Else
                json_StringIsLargeNumber = False
                Exit Function
            End Select
        Next json_CharIndex
    End If
End Function

Private Function json_ParseErrorMessage(json_String As String, ByRef json_Index As Long, ErrorMessage As String)
    ' Provide detailed parse error message, including details of where and what occurred
    '
    ' Example:
    ' Error parsing JSON:
    ' {"abcde":True}
    '          ^
    ' Expecting 'STRING', 'NUMBER', null, true, false, '{', or '['

    Dim json_StartIndex As Long
    Dim json_StopIndex As Long

    ' Include 10 characters before and after error (if possible)
    json_StartIndex = json_Index - 10
    json_StopIndex = json_Index + 10
    If json_StartIndex <= 0 Then
        json_StartIndex = 1
    End If
    If json_StopIndex > VBA.Len(json_String) Then
        json_StopIndex = VBA.Len(json_String)
    End If

    json_ParseErrorMessage = "Error parsing JSON:" & VBA.vbNewLine & _
                             VBA.Mid$(json_String, json_StartIndex, json_StopIndex - json_StartIndex + 1) & VBA.vbNewLine & _
                             VBA.Space$(json_Index - json_StartIndex) & "^" & VBA.vbNewLine & _
                             ErrorMessage
End Function

Private Sub json_BufferAppend(ByRef json_buffer As String, _
                              ByRef json_Append As Variant, _
                              ByRef json_BufferPosition As Long, _
                              ByRef json_BufferLength As Long)
#If Mac Then
    json_buffer = json_buffer & json_Append
#Else
    ' VBA can be slow to append strings due to allocating a new string for each append
    ' Instead of using the traditional append, allocate a large empty string and then copy string at append position
    '
    ' Example:
    ' Buffer: "abc  "
    ' Append: "def"
    ' Buffer Position: 3
    ' Buffer Length: 5
    '
    ' Buffer position + Append length > Buffer length -> Append chunk of blank space to buffer
    ' Buffer: "abc       "
    ' Buffer Length: 10
    '
    ' Copy memory for "def" into buffer at position 3 (0-based)
    ' Buffer: "abcdef    "
    '
    ' Approach based on cStringBuilder from vbAccelerator
    ' http://www.vbaccelerator.com/home/VB/Code/Techniques/RunTime_Debug_Tracing/VB6_Tracer_Utility_zip_cStringBuilder_cls.asp

    Dim json_AppendLength As Long
    Dim json_LengthPlusPosition As Long

    json_AppendLength = VBA.LenB(json_Append)
    json_LengthPlusPosition = json_AppendLength + json_BufferPosition

    If json_LengthPlusPosition > json_BufferLength Then
        ' Appending would overflow buffer, add chunks until buffer is long enough
        Dim json_TemporaryLength As Long

        json_TemporaryLength = json_BufferLength
        Do While json_TemporaryLength < json_LengthPlusPosition
            ' Initially, initialize string with 255 characters,
            ' then add large chunks (8192) after that
            '
            ' Size: # Characters x 2 bytes / character
            If json_TemporaryLength = 0 Then
                json_TemporaryLength = json_TemporaryLength + 510
            Else
                json_TemporaryLength = json_TemporaryLength + 16384
            End If
        Loop

        json_buffer = json_buffer & VBA.Space$((json_TemporaryLength - json_BufferLength) \ 2)
        json_BufferLength = json_TemporaryLength
    End If

    ' Copy memory from append to buffer at buffer position
    json_CopyMemory ByVal json_UnsignedAdd(StrPtr(json_buffer), _
                    json_BufferPosition), _
                    ByVal StrPtr(json_Append), _
                    json_AppendLength

    json_BufferPosition = json_BufferPosition + json_AppendLength
#End If
End Sub

Private Function json_BufferToString(ByRef json_buffer As String, ByVal json_BufferPosition As Long, ByVal json_BufferLength As Long) As String
#If Mac Then
    json_BufferToString = json_buffer
#Else
    If json_BufferPosition > 0 Then
        json_BufferToString = VBA.Left$(json_buffer, json_BufferPosition \ 2)
    End If
#End If
End Function

#If VBA7 Then
Private Function json_UnsignedAdd(json_Start As LongPtr, json_Increment As Long) As LongPtr
#Else
Private Function json_UnsignedAdd(json_Start As Long, json_Increment As Long) As Long
#End If

    If json_Start And &H80000000 Then
        json_UnsignedAdd = json_Start + json_Increment
    ElseIf (json_Start Or &H80000000) < -json_Increment Then
        json_UnsignedAdd = json_Start + json_Increment
    Else
        json_UnsignedAdd = (json_Start + &H80000000) + (json_Increment + &H80000000)
    End If
End Function

''
' VBA-UTC v1.0.3
' (c) Tim Hall - https://github.com/VBA-tools/VBA-UtcConverter
'
' UTC/ISO 8601 Converter for VBA
'
' Errors:
' 10011 - UTC parsing error
' 10012 - UTC conversion error
' 10013 - ISO 8601 parsing error
' 10014 - ISO 8601 conversion error
'
' @module UtcConverter
' @author tim.hall.engr@gmail.com
' @license MIT (http://www.opensource.org/licenses/mit-license.php)
'' ~~~~~~~~~~~~~~~~~~~~~~~~~~~~~~~~~~~~~~~~~~~~~~~~~~~~~~~~~~~~~~~~~~~~~~ '

' (Declarations moved to top)

' ============================================= '
' Public Methods
' ============================================= '

''
' Parse UTC date to local date
'
' @method ParseUtc
' @param {Date} UtcDate
' @return {Date} Local date
' @throws 10011 - UTC parsing error
''
Public Function ParseUtc(utc_UtcDate As Date) As Date
    On Error GoTo utc_ErrorHandling

#If Mac Then
    ParseUtc = utc_ConvertDate(utc_UtcDate)
#Else
    Dim utc_TimeZoneInfo As utc_TIME_ZONE_INFORMATION
    Dim utc_LocalDate As utc_SYSTEMTIME

    utc_GetTimeZoneInformation utc_TimeZoneInfo
    utc_SystemTimeToTzSpecificLocalTime utc_TimeZoneInfo, utc_DateToSystemTime(utc_UtcDate), utc_LocalDate

    ParseUtc = utc_SystemTimeToDate(utc_LocalDate)
#End If

    Exit Function

utc_ErrorHandling:
    Err.Raise 10011, "UtcConverter.ParseUtc", "UTC parsing error: " & Err.Number & " - " & Err.Description
End Function

''
' Convert local date to UTC date
'
' @method ConvertToUrc
' @param {Date} utc_LocalDate
' @return {Date} UTC date
' @throws 10012 - UTC conversion error
''
Public Function ConvertToUtc(utc_LocalDate As Date) As Date
    On Error GoTo utc_ErrorHandling

#If Mac Then
    ConvertToUtc = utc_ConvertDate(utc_LocalDate, utc_ConvertToUtc:=True)
#Else
    Dim utc_TimeZoneInfo As utc_TIME_ZONE_INFORMATION
    Dim utc_UtcDate As utc_SYSTEMTIME

    utc_GetTimeZoneInformation utc_TimeZoneInfo
    utc_TzSpecificLocalTimeToSystemTime utc_TimeZoneInfo, utc_DateToSystemTime(utc_LocalDate), utc_UtcDate

    ConvertToUtc = utc_SystemTimeToDate(utc_UtcDate)
#End If

    Exit Function

utc_ErrorHandling:
    Err.Raise 10012, "UtcConverter.ConvertToUtc", "UTC conversion error: " & Err.Number & " - " & Err.Description
End Function

''
' Parse ISO 8601 date string to local date
'
' @method ParseIso
' @param {Date} utc_IsoString
' @return {Date} Local date
' @throws 10013 - ISO 8601 parsing error
''
Public Function ParseIso(utc_IsoString As String) As Date
    On Error GoTo utc_ErrorHandling

    Dim utc_Parts() As String
    Dim utc_DateParts() As String
    Dim utc_TimeParts() As String
    Dim utc_OffsetIndex As Long
    Dim utc_HasOffset As Boolean
    Dim utc_NegativeOffset As Boolean
    Dim utc_OffsetParts() As String
    Dim utc_Offset As Date

    utc_Parts = VBA.Split(utc_IsoString, "T")
    utc_DateParts = VBA.Split(utc_Parts(0), "-")
    ParseIso = VBA.DateSerial(VBA.CInt(utc_DateParts(0)), VBA.CInt(utc_DateParts(1)), VBA.CInt(utc_DateParts(2)))

    If UBound(utc_Parts) > 0 Then
        If VBA.InStr(utc_Parts(1), "Z") Then
            utc_TimeParts = VBA.Split(VBA.Replace(utc_Parts(1), "Z", ""), ":")
        Else
            utc_OffsetIndex = VBA.InStr(1, utc_Parts(1), "+")
            If utc_OffsetIndex = 0 Then
                utc_NegativeOffset = True
                utc_OffsetIndex = VBA.InStr(1, utc_Parts(1), "-")
            End If

            If utc_OffsetIndex > 0 Then
                utc_HasOffset = True
                utc_TimeParts = VBA.Split(VBA.Left$(utc_Parts(1), utc_OffsetIndex - 1), ":")
                utc_OffsetParts = VBA.Split(VBA.Right$(utc_Parts(1), Len(utc_Parts(1)) - utc_OffsetIndex), ":")

                Select Case UBound(utc_OffsetParts)
                Case 0
                    utc_Offset = TimeSerial(VBA.CInt(utc_OffsetParts(0)), 0, 0)
                Case 1
                    utc_Offset = TimeSerial(VBA.CInt(utc_OffsetParts(0)), VBA.CInt(utc_OffsetParts(1)), 0)
                Case 2
                    ' VBA.Val does not use regional settings, use for seconds to avoid decimal/comma issues
                    utc_Offset = TimeSerial(VBA.CInt(utc_OffsetParts(0)), VBA.CInt(utc_OffsetParts(1)), Int(VBA.Val(utc_OffsetParts(2))))
                End Select

                If utc_NegativeOffset Then: utc_Offset = -utc_Offset
            Else
                utc_TimeParts = VBA.Split(utc_Parts(1), ":")
            End If
        End If

        Select Case UBound(utc_TimeParts)
        Case 0
            ParseIso = ParseIso + VBA.TimeSerial(VBA.CInt(utc_TimeParts(0)), 0, 0)
        Case 1
            ParseIso = ParseIso + VBA.TimeSerial(VBA.CInt(utc_TimeParts(0)), VBA.CInt(utc_TimeParts(1)), 0)
        Case 2
            ' VBA.Val does not use regional settings, use for seconds to avoid decimal/comma issues
            ParseIso = ParseIso + VBA.TimeSerial(VBA.CInt(utc_TimeParts(0)), VBA.CInt(utc_TimeParts(1)), Int(VBA.Val(utc_TimeParts(2))))
        End Select

        ParseIso = ParseUtc(ParseIso)

        If utc_HasOffset Then
            ParseIso = ParseIso + utc_Offset
        End If
    End If

    Exit Function

utc_ErrorHandling:
    Err.Raise 10013, "UtcConverter.ParseIso", "ISO 8601 parsing error for " & utc_IsoString & ": " & Err.Number & " - " & Err.Description
End Function

''
' Convert local date to ISO 8601 string
'
' @method ConvertToIso
' @param {Date} utc_LocalDate
' @return {Date} ISO 8601 string
' @throws 10014 - ISO 8601 conversion error
''
Public Function ConvertToIso(utc_LocalDate As Date) As String
    On Error GoTo utc_ErrorHandling

    ConvertToIso = VBA.Format$(ConvertToUtc(utc_LocalDate), "yyyy-mm-ddTHH:mm:ss.000Z")

    Exit Function

utc_ErrorHandling:
    Err.Raise 10014, "UtcConverter.ConvertToIso", "ISO 8601 conversion error: " & Err.Number & " - " & Err.Description
End Function

' ============================================= '
' Private Functions
' ============================================= '

#If Mac Then

Private Function utc_ConvertDate(utc_Value As Date, Optional utc_ConvertToUtc As Boolean = False) As Date
    Dim utc_ShellCommand As String
    Dim utc_Result As utc_ShellResult
    Dim utc_Parts() As String
    Dim utc_DateParts() As String
    Dim utc_TimeParts() As String

    If utc_ConvertToUtc Then
        utc_ShellCommand = "date -ur `date -jf '%Y-%m-%d %H:%M:%S' " & _
            "'" & VBA.Format$(utc_Value, "yyyy-mm-dd HH:mm:ss") & "' " & _
            " +'%s'` +'%Y-%m-%d %H:%M:%S'"
    Else
        utc_ShellCommand = "date -jf '%Y-%m-%d %H:%M:%S %z' " & _
            "'" & VBA.Format$(utc_Value, "yyyy-mm-dd HH:mm:ss") & " +0000' " & _
            "+'%Y-%m-%d %H:%M:%S'"
    End If

    utc_Result = utc_ExecuteInShell(utc_ShellCommand)

    If utc_Result.utc_Output = "" Then
        Err.Raise 10015, "UtcConverter.utc_ConvertDate", "'date' command failed"
    Else
        utc_Parts = Split(utc_Result.utc_Output, " ")
        utc_DateParts = Split(utc_Parts(0), "-")
        utc_TimeParts = Split(utc_Parts(1), ":")

        utc_ConvertDate = DateSerial(utc_DateParts(0), utc_DateParts(1), utc_DateParts(2)) + _
            TimeSerial(utc_TimeParts(0), utc_TimeParts(1), utc_TimeParts(2))
    End If
End Function

Private Function utc_ExecuteInShell(utc_ShellCommand As String) As utc_ShellResult
#If VBA7 Then
    Dim utc_File As LongPtr
    Dim utc_Read As LongPtr
#Else
    Dim utc_File As Long
    Dim utc_Read As Long
#End If

    Dim utc_Chunk As String

    On Error GoTo utc_ErrorHandling
    utc_File = utc_popen(utc_ShellCommand, "r")

    If utc_File = 0 Then: Exit Function

    Do While utc_feof(utc_File) = 0
        utc_Chunk = VBA.Space$(50)
        utc_Read = utc_fread(utc_Chunk, 1, Len(utc_Chunk) - 1, utc_File)
        If utc_Read > 0 Then
            utc_Chunk = VBA.Left$(utc_Chunk, utc_Read)
            utc_ExecuteInShell.utc_Output = utc_ExecuteInShell.utc_Output & utc_Chunk
        End If
    Loop

utc_ErrorHandling:
    utc_ExecuteInShell.utc_ExitCode = utc_pclose(utc_File)
End Function

#Else

Private Function utc_DateToSystemTime(utc_Value As Date) As utc_SYSTEMTIME
    utc_DateToSystemTime.utc_wYear = VBA.Year(utc_Value)
    utc_DateToSystemTime.utc_wMonth = VBA.Month(utc_Value)
    utc_DateToSystemTime.utc_wDay = VBA.Day(utc_Value)
    utc_DateToSystemTime.utc_wHour = VBA.Hour(utc_Value)
    utc_DateToSystemTime.utc_wMinute = VBA.Minute(utc_Value)
    utc_DateToSystemTime.utc_wSecond = VBA.Second(utc_Value)
    utc_DateToSystemTime.utc_wMilliseconds = 0
End Function

Private Function utc_SystemTimeToDate(utc_Value As utc_SYSTEMTIME) As Date
    utc_SystemTimeToDate = DateSerial(utc_Value.utc_wYear, utc_Value.utc_wMonth, utc_Value.utc_wDay) + _
        TimeSerial(utc_Value.utc_wHour, utc_Value.utc_wMinute, utc_Value.utc_wSecond)
End Function

#End If

Attribute VB_Name = "Module1"
Option Explicit

''''''''''''''''''''''''''''''''''''''''''''''''''''''''''''''''''''''''''''''''''''''''''''''
''''''''''''''''''''''''''''''''''''''''''''''''''''''''''''''''''''''''''''''''''''''''''''''
'''''''''''''''''''CHECKS THE REVISION NUMBER IN EXCEL AND PLACES THE'''''''''''''''''''''''''
''''''''''''''''''''MODULE, PITCH AND ORIENTATION NUMBERS IN THE PROPER'''''''''''''''''''''''
'''''''''''''''''''''SPOT IN THE "REVISION LIST" SHEET''''''''''''''''''''''''''''''''''''''''
''''''''''''''''''''''''''''''''''''''''''''''''''''''''''''''''''''''''''''''''''''''''''''''
''''''''''''''''''''''''''''''''''''''''''''''''''''''''''''''''''''''''''''''''''''''''''''''
'''''''''MADE BY TAMIR LIEBER'''''''''''''''''''''''''''''''''''''''''''''''''''''''''''''''''
''''''''''''''''''''''''''''''''''''''''''''''''''''''''''''''''''''''''''''''''''''''''''''''

Sub revisionlist()

    Dim I As Integer
        For I = 1 To 3
            Call revisionfxn(31 - I)
        Next I
        
End Sub
Public Function revisionfxn(cellnum)

''''''''''''''''''''''''''''''''''''''''''''''''''''''''''''
'''''''''''''''''''''''DECLARE VARIABLES''''''''''''''''''''
''''''''''''''''''''''''''''''''''''''''''''''''''''''''''''
Dim path1 As String
Dim path2 As String
Dim path3 As String
path1 = ThisDrawing.Path 'GETS THE FOLDER EXTENSION THE DRAWING IS IN
path2 = "\ACAD CALC TEMPLATE.xlsx"
path3 = path1 + path2
Dim xlapp As Object
Dim wkb As Object
Dim formsheet As Object
Dim currExcelSheet As Object
Dim revisionsheet As Object
    '''''''''''''''''''''''''''''''''''''''''''''''''''''''''''''''''''''''''''''''
    ''''''''''''''''''SETUP EXCEL WORKBOOK AND EXCEL SHEETS''''''''''''''''''''''''
    '''''''''''''''''''''''''''''''''''''''''''''''''''''''''''''''''''''''''''''''
    Set xlapp = Excel.Application
    Set wkb = xlapp.Workbooks.Open(path3)
    xlapp.Visible = False
    Set formsheet = Excel.Application.Sheets("FORM")
    Set currExcelSheet = Excel.Application.Sheets("CURRENT EXCEL ROOFS")
    Set revisionsheet = Excel.Application.Sheets("REVISION LIST")
        ''''''''''''''''''''''''''''''''''''''''''''''''''''''''''''''''''''''''''''''''''''''''''''''
        '''''''''''''''''''''''CHECKING "FORM" SHEET CELL D31 FOR PERMIT SETS'''''''''''''''''''''''''
        ''''''''''''''''''''''''''''''''''''''''''''''''''''''''''''''''''''''''''''''''''''''''''''''
            ''''''''''''P1'''''''''''
            ''''''''''''''''''''''''''''''''
                '''''''''''ROOFS''''''''''''
                ''''''''''''''''''''''''''''
                If formsheet.Cells(31, 4).Value = "P1" Then
                    If revisionsheet.Cells(3, 2).Value = "" Then
                        currExcelSheet.Range("K3:K25").Copy
                        revisionsheet.Range("A3:A25").PasteSpecial Paste:=xlPasteValues
                        Dim A As Range
                        For Each A In revisionsheet.Range("A3:A25")
                        A = Replace(A, " ", "")
                        Next
                    Else
                    End If
                Else
                End If
                '''''''''''MODULES''''''''''
                ''''''''''''''''''''''''''''
                If formsheet.Cells(31, 4).Value = "P1" Then
                    If revisionsheet.Cells(3, 2).Value = "" Then
                        currExcelSheet.Range("L3:L25").Copy
                        revisionsheet.Range("B3:B25").PasteSpecial Paste:=xlPasteValues
                        
                    Else
                    End If
                Else
                End If
                ''''''''''''''''''''''''''''
                ''''''''''''PITCH'''''''''''
                ''''''''''''''''''''''''''''
                If formsheet.Cells(31, 4).Value = "P1" Then
                    If revisionsheet.Cells(3, 3).Value = "" Then
                        currExcelSheet.Range("M3:M25").Copy
                        revisionsheet.Range("C3:C25").PasteSpecial Paste:=xlPasteValues
                    Else
                    End If
                Else
                End If
                ''''''''''''''''''''''''''''
                '''''''''ORIENTATION''''''''
                ''''''''''''''''''''''''''''
                If formsheet.Cells(31, 4).Value = "P1" Then
                    If revisionsheet.Cells(3, 4).Value = "" Then
                        currExcelSheet.Range("N3:N25").Copy
                        revisionsheet.Range("D3:D25").PasteSpecial Paste:=xlPasteValues
                    Else
                    End If
                Else
                End If
        ''''''''''''''''''''''''''''''''''''''''''''''''''''''''''''''''''''''''''''''''''''''''''''''
        '''''''''''''''''''''''CHECKING "FORM" SHEET CELL D30-D28 FOR PERMIT SETS'''''''''''''''''''''
        ''''''''''''''''''''''''''''''''''''''''''''''''''''''''''''''''''''''''''''''''''''''''''''''
            '''''''''''''''''''''''''
            ''''''''''''P2'''''''''''
            ''''''''''''''''''''''''''''''''
                '''''''''''ROOFS''''''''''''
                ''''''''''''''''''''''''''''
                If formsheet.Cells(cellnum, 4).Value = "P2" Then
                    If revisionsheet.Cells(3, 5).Value = "" Then
                        currExcelSheet.Range("K3:K25").Copy
                        revisionsheet.Range("E3:E25").PasteSpecial Paste:=xlPasteValues
                        Dim E As Range
                        For Each E In revisionsheet.Range("E3:E25")
                        E = Replace(E, " ", "")
                        Next
                        
                    Else
                    End If
                Else
                End If
                ''''''''''''''''''''''''''''
                '''''''''''MODULES''''''''''
                ''''''''''''''''''''''''''''
                If formsheet.Cells(cellnum, 4).Value = "P2" Then
                    If revisionsheet.Cells(3, 6).Value = "" Then
                        currExcelSheet.Range("L3:L25").Copy
                        revisionsheet.Range("F3:F25").PasteSpecial Paste:=xlPasteValues
                    Else
                    End If
                Else
                End If
                ''''''''''''''''''''''''''''
                ''''''''''''PITCH'''''''''''
                ''''''''''''''''''''''''''''
                If formsheet.Cells(cellnum, 4).Value = "P2" Then
                    If revisionsheet.Cells(3, 7).Value = "" Then
                        currExcelSheet.Range("M3:M25").Copy
                        revisionsheet.Range("G3:G25").PasteSpecial Paste:=xlPasteValues
                    Else
                    End If
                Else
                End If
                ''''''''''''''''''''''''''''
                '''''''''ORIENTATION''''''''
                ''''''''''''''''''''''''''''
                If formsheet.Cells(cellnum, 4).Value = "P2" Then
                    If revisionsheet.Cells(3, 8).Value = "" Then
                        currExcelSheet.Range("N3:N25").Copy
                        revisionsheet.Range("H3:H25").PasteSpecial Paste:=xlPasteValues
                    Else
                    End If
                Else
                End If
            ''''''''''''''''''''''''''''
            '''''''''''''P3'''''''''''''
            ''''''''''''''''''''''''''''
                '''''''''''ROOFS''''''''''''
                ''''''''''''''''''''''''''''
                If formsheet.Cells(cellnum, 4).Value = "P3" Then
                    If revisionsheet.Cells(3, 9).Value = "" Then
                        currExcelSheet.Range("K3:K25").Copy
                        revisionsheet.Range("I3:I25").PasteSpecial Paste:=xlPasteValues
                        Dim I As Range
                        For Each I In revisionsheet.Range("I3:I25")
                        I = Replace(I, " ", "")
                        Next
                    Else
                    End If
                Else
                End If
                '''''''''''MODULES''''''''''
                ''''''''''''''''''''''''''''
                If formsheet.Cells(cellnum, 4).Value = "P3" Then
                    If revisionsheet.Cells(3, 10).Value = "" Then
                        currExcelSheet.Range("L3:L25").Copy
                        revisionsheet.Range("J3:J25").PasteSpecial Paste:=xlPasteValues
                    Else
                    End If
                Else
                End If
                ''''''''''''''''''''''''''''
                ''''''''''''PITCH'''''''''''
                ''''''''''''''''''''''''''''
                If formsheet.Cells(cellnum, 4).Value = "P3" Then
                    If revisionsheet.Cells(3, 11).Value = "" Then
                        currExcelSheet.Range("M3:M25").Copy
                        revisionsheet.Range("K3:K25").PasteSpecial Paste:=xlPasteValues
                    Else
                    End If
                Else
                End If
                ''''''''''''''''''''''''''''
                '''''''''ORIENTATION''''''''
                ''''''''''''''''''''''''''''
                If formsheet.Cells(cellnum, 4).Value = "P3" Then
                    If revisionsheet.Cells(3, 12).Value = "" Then
                        currExcelSheet.Range("N3:N25").Copy
                        revisionsheet.Range("L3:L25").PasteSpecial Paste:=xlPasteValues
                    Else
                    End If
                Else
                End If
            ''''''''''''''''''''''''''''
            '''''''''''''P4'''''''''''''
            ''''''''''''''''''''''''''''
                '''''''''''ROOFS''''''''''''
                ''''''''''''''''''''''''''''
                If formsheet.Cells(cellnum, 4).Value = "P4" Then
                    If revisionsheet.Cells(3, 13).Value = "" Then
                        currExcelSheet.Range("K3:K25").Copy
                        revisionsheet.Range("M3:M25").PasteSpecial Paste:=xlPasteValues
                        Dim M As Range
                        For Each M In revisionsheet.Range("M3:M25")
                        M = Replace(M, " ", "")
                        Next
                    Else
                    End If
                Else
                End If
                ''''''''''''''''''''''''''''
                '''''''''''MODULES''''''''''
                ''''''''''''''''''''''''''''
                If formsheet.Cells(cellnum, 4).Value = "P4" Then
                    If revisionsheet.Cells(3, 14).Value = "" Then
                        currExcelSheet.Range("L3:L25").Copy
                        revisionsheet.Range("N3:N25").PasteSpecial Paste:=xlPasteValues
                    Else
                    End If
                Else
                End If
                ''''''''''''''''''''''''''''
                ''''''''''''PITCH'''''''''''
                ''''''''''''''''''''''''''''
                If formsheet.Cells(cellnum, 4).Value = "P4" Then
                    If revisionsheet.Cells(3, 15).Value = "" Then
                        currExcelSheet.Range("M3:M25").Copy
                        revisionsheet.Range("O3:O25").PasteSpecial Paste:=xlPasteValues
                    Else
                    End If
                Else
                End If
                ''''''''''''''''''''''''''''
                '''''''''ORIENTATION''''''''
                ''''''''''''''''''''''''''''
                If formsheet.Cells(cellnum, 4).Value = "P4" Then
                    If revisionsheet.Cells(3, 16).Value = "" Then
                        currExcelSheet.Range("N3:N25").Copy
                        revisionsheet.Range("P3:P25").PasteSpecial Paste:=xlPasteValues
                    Else
                    End If
                Else
                End If
            ''''''''''''''''''''''''''''
            '''''''''''''P5'''''''''''''
            ''''''''''''''''''''''''''''
                '''''''''''ROOFS''''''''''''
                ''''''''''''''''''''''''''''
                If formsheet.Cells(cellnum, 4).Value = "P5" Then
                    If revisionsheet.Cells(3, 17).Value = "" Then
                        currExcelSheet.Range("K3:K25").Copy
                        revisionsheet.Range("Q3:Q25").PasteSpecial Paste:=xlPasteValues
                        Dim Q As Range
                        For Each Q In revisionsheet.Range("Q3:Q25")
                        Q = Replace(Q, " ", "")
                        Next
                    Else
                    End If
                Else
                End If
                ''''''''''''''''''''''''''''
                '''''''''''MODULES''''''''''
                ''''''''''''''''''''''''''''
                If formsheet.Cells(cellnum, 4).Value = "P5" Then
                    If revisionsheet.Cells(3, 18).Value = "" Then
                        currExcelSheet.Range("L3:L25").Copy
                        revisionsheet.Range("R3:R25").PasteSpecial Paste:=xlPasteValues
                    Else
                    End If
                Else
                End If
                ''''''''''''''''''''''''''''
                ''''''''''''PITCH'''''''''''
                ''''''''''''''''''''''''''''
                If formsheet.Cells(cellnum, 4).Value = "P5" Then
                    If revisionsheet.Cells(3, 19).Value = "" Then
                        currExcelSheet.Range("M3:M25").Copy
                        revisionsheet.Range("S3:S25").PasteSpecial Paste:=xlPasteValues
                    Else
                    End If
                Else
                End If
                ''''''''''''''''''''''''''''
                '''''''''ORIENTATION''''''''
                ''''''''''''''''''''''''''''
                If formsheet.Cells(cellnum, 4).Value = "P5" Then
                    If revisionsheet.Cells(3, 20).Value = "" Then
                        currExcelSheet.Range("N3:N25").Copy
                        revisionsheet.Range("T3:T25").PasteSpecial Paste:=xlPasteValues
                    Else
                    End If
                Else
                End If
            ''''''''''''''''''''''''''''
            '''''''''''''R1'''''''''''''
            ''''''''''''''''''''''''''''
                '''''''''''ROOFS''''''''''''
                ''''''''''''''''''''''''''''
                If formsheet.Cells(cellnum, 4).Value = "R1" Then
                    If revisionsheet.Cells(3, 21).Value = "" Then
                        currExcelSheet.Range("K3:K25").Copy
                        revisionsheet.Range("U3:U25").PasteSpecial Paste:=xlPasteValues
                        Dim U As Range
                        For Each U In revisionsheet.Range("U3:U25")
                        U = Replace(U, " ", "")
                        Next
                    Else
                    End If
                Else
                End If
                '''''''''''MODULES''''''''''
                ''''''''''''''''''''''''''''
                If formsheet.Cells(cellnum, 4).Value = "R1" Then
                    If revisionsheet.Cells(3, 22).Value = "" Then
                        currExcelSheet.Range("L3:L25").Copy
                        revisionsheet.Range("V3:V25").PasteSpecial Paste:=xlPasteValues
                    Else
                    End If
                Else
                End If
                ''''''''''''''''''''''''''''
                ''''''''''''PITCH'''''''''''
                ''''''''''''''''''''''''''''
                If formsheet.Cells(cellnum, 4).Value = "R1" Then
                    If revisionsheet.Cells(3, 23).Value = "" Then
                        currExcelSheet.Range("M3:M25").Copy
                        revisionsheet.Range("W3:W25").PasteSpecial Paste:=xlPasteValues
                    Else
                    End If
                Else
                End If
                ''''''''''''''''''''''''''''
                '''''''''ORIENTATION''''''''
                ''''''''''''''''''''''''''''
                If formsheet.Cells(cellnum, 4).Value = "R1" Then
                    If revisionsheet.Cells(3, 24).Value = "" Then
                        currExcelSheet.Range("N3:N25").Copy
                        revisionsheet.Range("X3:X25").PasteSpecial Paste:=xlPasteValues
                    Else
                    End If
                Else
                End If
            ''''''''''''''''''''''''''''
            '''''''''''''R2'''''''''''''
            ''''''''''''''''''''''''''''
                '''''''''''ROOFS''''''''''''
                ''''''''''''''''''''''''''''
                If formsheet.Cells(cellnum, 4).Value = "R2" Then
                    If revisionsheet.Cells(3, 25).Value = "" Then
                        currExcelSheet.Range("K3:K25").Copy
                        revisionsheet.Range("Y3:Y25").PasteSpecial Paste:=xlPasteValues
                        Dim Y As Range
                        For Each Y In revisionsheet.Range("Y3:Y25")
                        Y = Replace(Y, " ", "")
                        Next
                    Else
                    End If
                Else
                End If
                '''''''''''MODULES''''''''''
                ''''''''''''''''''''''''''''
                If formsheet.Cells(cellnum, 4).Value = "R2" Then
                    If revisionsheet.Cells(3, 26).Value = "" Then
                        currExcelSheet.Range("L3:L25").Copy
                        revisionsheet.Range("Z3:Z25").PasteSpecial Paste:=xlPasteValues
                    Else
                    End If
                Else
                End If
                ''''''''''''''''''''''''''''
                ''''''''''''PITCH'''''''''''
                ''''''''''''''''''''''''''''
                If formsheet.Cells(cellnum, 4).Value = "R2" Then
                    If revisionsheet.Cells(3, 27).Value = "" Then
                        currExcelSheet.Range("M3:M25").Copy
                        revisionsheet.Range("AA3:AA25").PasteSpecial Paste:=xlPasteValues
                    Else
                    End If
                Else
                End If
                ''''''''''''''''''''''''''''
                '''''''''ORIENTATION''''''''
                ''''''''''''''''''''''''''''
                If formsheet.Cells(cellnum, 4).Value = "R2" Then
                    If revisionsheet.Cells(3, 28).Value = "" Then
                        currExcelSheet.Range("N3:N25").Copy
                        revisionsheet.Range("AB3:AB25").PasteSpecial Paste:=xlPasteValues
                    Else
                    End If
                Else
                End If
            ''''''''''''''''''''''''''''
            '''''''''''''R3'''''''''''''
            ''''''''''''''''''''''''''''
                '''''''''''ROOFS''''''''''''
                ''''''''''''''''''''''''''''
                If formsheet.Cells(cellnum, 4).Value = "R3" Then
                    If revisionsheet.Cells(3, 29).Value = "" Then
                        currExcelSheet.Range("K3:K25").Copy
                        revisionsheet.Range("AC3:AC25").PasteSpecial Paste:=xlPasteValues
                        Dim AC As Range
                        For Each AC In revisionsheet.Range("AC3:AC25")
                        AC = Replace(AC, " ", "")
                        Next
                    Else
                    End If
                Else
                End If
                '''''''''''MODULES''''''''''
                ''''''''''''''''''''''''''''
                If formsheet.Cells(cellnum, 4).Value = "R3" Then
                    If revisionsheet.Cells(3, 30).Value = "" Then
                        currExcelSheet.Range("L3:L25").Copy
                        revisionsheet.Range("AD3:AD25").PasteSpecial Paste:=xlPasteValues
                    Else
                    End If
                Else
                End If
                ''''''''''''''''''''''''''''
                ''''''''''''PITCH'''''''''''
                ''''''''''''''''''''''''''''
                If formsheet.Cells(cellnum, 4).Value = "R3" Then
                    If revisionsheet.Cells(3, 31).Value = "" Then
                        currExcelSheet.Range("M3:M25").Copy
                        revisionsheet.Range("AE3:AE25").PasteSpecial Paste:=xlPasteValues
                    Else
                    End If
                Else
                End If
                ''''''''''''''''''''''''''''
                '''''''''ORIENTATION''''''''
                ''''''''''''''''''''''''''''
                If formsheet.Cells(cellnum, 4).Value = "R3" Then
                    If revisionsheet.Cells(3, 32).Value = "" Then
                        currExcelSheet.Range("N3:N25").Copy
                        revisionsheet.Range("AF3:AF25").PasteSpecial Paste:=xlPasteValues
                    Else
                    End If
                Else
                End If
            ''''''''''''''''''''''''''''
            '''''''''''''R4'''''''''''''
            ''''''''''''''''''''''''''''
                '''''''''''ROOFS''''''''''''
                ''''''''''''''''''''''''''''
                If formsheet.Cells(cellnum, 4).Value = "R4" Then
                    If revisionsheet.Cells(3, 33).Value = "" Then
                        currExcelSheet.Range("K3:K25").Copy
                        revisionsheet.Range("AG3:AG25").PasteSpecial Paste:=xlPasteValues
                        Dim AG As Range
                        For Each AG In revisionsheet.Range("AG3:AG25")
                        AG = Replace(AG, " ", "")
                        Next
                    Else
                    End If
                Else
                End If
                '''''''''''MODULES''''''''''
                ''''''''''''''''''''''''''''
                If formsheet.Cells(cellnum, 4).Value = "R4" Then
                    If revisionsheet.Cells(3, 34).Value = "" Then
                        currExcelSheet.Range("L3:L25").Copy
                        revisionsheet.Range("AH3:AH25").PasteSpecial Paste:=xlPasteValues
                    Else
                    End If
                Else
                End If
                ''''''''''''''''''''''''''''
                ''''''''''''PITCH'''''''''''
                ''''''''''''''''''''''''''''
                If formsheet.Cells(cellnum, 4).Value = "R4" Then
                    If revisionsheet.Cells(3, 35).Value = "" Then
                        currExcelSheet.Range("M3:M25").Copy
                        revisionsheet.Range("AI3:AI25").PasteSpecial Paste:=xlPasteValues
                    Else
                    End If
                Else
                End If
                ''''''''''''''''''''''''''''
                '''''''''ORIENTATION''''''''
                ''''''''''''''''''''''''''''
                If formsheet.Cells(cellnum, 4).Value = "R4" Then
                    If revisionsheet.Cells(3, 36).Value = "" Then
                        currExcelSheet.Range("N3:N25").Copy
                        revisionsheet.Range("AJ3:AJ25").PasteSpecial Paste:=xlPasteValues
                    Else
                    End If
                Else
                End If
            ''''''''''''''''''''''''''''
            '''''''''''''R5'''''''''''''
            ''''''''''''''''''''''''''''
                '''''''''''ROOFS''''''''''''
                ''''''''''''''''''''''''''''
                If formsheet.Cells(cellnum, 4).Value = "R5" Then
                    If revisionsheet.Cells(3, 37).Value = "" Then
                        currExcelSheet.Range("K3:K25").Copy
                        revisionsheet.Range("AK3:AK25").PasteSpecial Paste:=xlPasteValues
                        Dim AK As Range
                        For Each AK In revisionsheet.Range("AK3:AK25")
                        AK = Replace(AK, " ", "")
                        Next
                    Else
                    End If
                Else
                End If
                '''''''''''MODULES''''''''''
                ''''''''''''''''''''''''''''
                If formsheet.Cells(cellnum, 4).Value = "R5" Then
                    If revisionsheet.Cells(3, 38).Value = "" Then
                        currExcelSheet.Range("L3:L25").Copy
                        revisionsheet.Range("AL3:AL25").PasteSpecial Paste:=xlPasteValues
                    Else
                    End If
                Else
                End If
                ''''''''''''''''''''''''''''
                ''''''''''''PITCH'''''''''''
                ''''''''''''''''''''''''''''
                If formsheet.Cells(cellnum, 4).Value = "R5" Then
                    If revisionsheet.Cells(3, 39).Value = "" Then
                        currExcelSheet.Range("M3:M25").Copy
                        revisionsheet.Range("AM3:AM25").PasteSpecial Paste:=xlPasteValues
                    Else
                    End If
                Else
                End If
                ''''''''''''''''''''''''''''
                '''''''''ORIENTATION''''''''
                ''''''''''''''''''''''''''''
                If formsheet.Cells(cellnum, 4).Value = "R5" Then
                    If revisionsheet.Cells(3, 40).Value = "" Then
                        currExcelSheet.Range("N3:N25").Copy
                        revisionsheet.Range("AN3:AN25").PasteSpecial Paste:=xlPasteValues
                    Else
                    End If
                Else
                End If
            ''''''''''''''''''''''''''''
            '''''''''''''A1'''''''''''''
            ''''''''''''''''''''''''''''
                '''''''''''ROOFS''''''''''''
                ''''''''''''''''''''''''''''
                If formsheet.Cells(cellnum, 4).Value = "A1" Then
                    If revisionsheet.Cells(3, 41).Value = "" Then
                        currExcelSheet.Range("K3:K25").Copy
                        revisionsheet.Range("AO3:AO25").PasteSpecial Paste:=xlPasteValues
                        Dim AO As Range
                        For Each AO In revisionsheet.Range("AO3:AO25")
                        AO = Replace(AO, " ", "")
                        Next
                    Else
                    End If
                Else
                End If
                '''''''''''MODULES''''''''''
                ''''''''''''''''''''''''''''
                If formsheet.Cells(cellnum, 4).Value = "A1" Then
                    If revisionsheet.Cells(3, 42).Value = "" Then
                        currExcelSheet.Range("L3:L25").Copy
                        revisionsheet.Range("AP3:AP25").PasteSpecial Paste:=xlPasteValues
                    Else
                    End If
                Else
                End If
                ''''''''''''''''''''''''''''
                ''''''''''''PITCH'''''''''''
                ''''''''''''''''''''''''''''
                If formsheet.Cells(cellnum, 4).Value = "A1" Then
                    If revisionsheet.Cells(3, 43).Value = "" Then
                        currExcelSheet.Range("M3:M25").Copy
                        revisionsheet.Range("AQ3:AQ25").PasteSpecial Paste:=xlPasteValues
                    Else
                    End If
                Else
                End If
                ''''''''''''''''''''''''''''
                '''''''''ORIENTATION''''''''
                ''''''''''''''''''''''''''''
                If formsheet.Cells(cellnum, 4).Value = "A1" Then
                    If revisionsheet.Cells(3, 44).Value = "" Then
                        currExcelSheet.Range("N3:N25").Copy
                        revisionsheet.Range("AR3:AR25").PasteSpecial Paste:=xlPasteValues
                    Else
                    End If
                Else
                End If
            ''''''''''''''''''''''''''''
            '''''''''''''A2'''''''''''''
            ''''''''''''''''''''''''''''
                '''''''''''ROOFS''''''''''''
                ''''''''''''''''''''''''''''
                If formsheet.Cells(cellnum, 4).Value = "A2" Then
                    If revisionsheet.Cells(3, 45).Value = "" Then
                        currExcelSheet.Range("K3:K25").Copy
                        revisionsheet.Range("AS3:AS25").PasteSpecial Paste:=xlPasteValues
                        Dim AS1 As Range
                        For Each AS1 In revisionsheet.Range("AS3:AS25")
                        AS1 = Replace(AS1, " ", "")
                        Next
                    Else
                    End If
                Else
                End If
                '''''''''''MODULES''''''''''
                ''''''''''''''''''''''''''''
                If formsheet.Cells(cellnum, 4).Value = "A2" Then
                    If revisionsheet.Cells(3, 46).Value = "" Then
                        currExcelSheet.Range("L3:L25").Copy
                        revisionsheet.Range("AT3:AT25").PasteSpecial Paste:=xlPasteValues
                    Else
                    End If
                Else
                End If
                ''''''''''''''''''''''''''''
                ''''''''''''PITCH'''''''''''
                ''''''''''''''''''''''''''''
                If formsheet.Cells(cellnum, 4).Value = "A2" Then
                    If revisionsheet.Cells(3, 47).Value = "" Then
                        currExcelSheet.Range("M3:M25").Copy
                        revisionsheet.Range("AU3:AU25").PasteSpecial Paste:=xlPasteValues
                    Else
                    End If
                Else
                End If
                ''''''''''''''''''''''''''''
                '''''''''ORIENTATION''''''''
                ''''''''''''''''''''''''''''
                If formsheet.Cells(cellnum, 4).Value = "A2" Then
                    If revisionsheet.Cells(3, 48).Value = "" Then
                        currExcelSheet.Range("N3:N25").Copy
                        revisionsheet.Range("AV3:AV25").PasteSpecial Paste:=xlPasteValues
                    Else
                    End If
                Else
                End If
            ''''''''''''''''''''''''''''
            '''''''''''''A3'''''''''''''
            ''''''''''''''''''''''''''''
                '''''''''''ROOFS''''''''''''
                ''''''''''''''''''''''''''''
                If formsheet.Cells(cellnum, 4).Value = "A3" Then
                    If revisionsheet.Cells(3, 49).Value = "" Then
                        currExcelSheet.Range("K3:K25").Copy
                        revisionsheet.Range("AW3:AW25").PasteSpecial Paste:=xlPasteValues
                        Dim AW As Range
                        For Each AW In revisionsheet.Range("AW3:AW25")
                        AW = Replace(AW, " ", "")
                        Next
                    Else
                    End If
                Else
                End If
                '''''''''''MODULES''''''''''
                ''''''''''''''''''''''''''''
                If formsheet.Cells(cellnum, 4).Value = "A3" Then
                    If revisionsheet.Cells(3, 50).Value = "" Then
                        currExcelSheet.Range("L3:L25").Copy
                        revisionsheet.Range("AX3:AX25").PasteSpecial Paste:=xlPasteValues
                    Else
                    End If
                Else
                End If
                ''''''''''''''''''''''''''''
                ''''''''''''PITCH'''''''''''
                ''''''''''''''''''''''''''''
                If formsheet.Cells(cellnum, 4).Value = "A3" Then
                    If revisionsheet.Cells(3, 51).Value = "" Then
                        currExcelSheet.Range("M3:M25").Copy
                        revisionsheet.Range("AY3:AY25").PasteSpecial Paste:=xlPasteValues
                    Else
                    End If
                Else
                End If
                ''''''''''''''''''''''''''''
                '''''''''ORIENTATION''''''''
                ''''''''''''''''''''''''''''
                If formsheet.Cells(cellnum, 4).Value = "A3" Then
                    If revisionsheet.Cells(3, 52).Value = "" Then
                        currExcelSheet.Range("N3:N25").Copy
                        revisionsheet.Range("AZ3:AZ25").PasteSpecial Paste:=xlPasteValues
                    Else
                    End If
                Else
                End If
            ''''''''''''''''''''''''''''
            '''''''''''''A4'''''''''''''
            ''''''''''''''''''''''''''''
                '''''''''''ROOFS''''''''''''
                ''''''''''''''''''''''''''''
                If formsheet.Cells(cellnum, 4).Value = "A4" Then
                    If revisionsheet.Cells(3, 53).Value = "" Then
                        currExcelSheet.Range("K3:K25").Copy
                        revisionsheet.Range("BA3:BA25").PasteSpecial Paste:=xlPasteValues
                        Dim BA As Range
                        For Each BA In revisionsheet.Range("BA3:BA25")
                        BA = Replace(BA, " ", "")
                        Next
                    Else
                    End If
                Else
                End If
                '''''''''''MODULES''''''''''
                ''''''''''''''''''''''''''''
                If formsheet.Cells(cellnum, 4).Value = "A4" Then
                    If revisionsheet.Cells(3, 54).Value = "" Then
                        currExcelSheet.Range("L3:L25").Copy
                        revisionsheet.Range("BB3:BB25").PasteSpecial Paste:=xlPasteValues
                    Else
                    End If
                Else
                End If
                ''''''''''''''''''''''''''''
                ''''''''''''PITCH'''''''''''
                ''''''''''''''''''''''''''''
                If formsheet.Cells(cellnum, 4).Value = "A4" Then
                    If revisionsheet.Cells(3, 55).Value = "" Then
                        currExcelSheet.Range("M3:M25").Copy
                        revisionsheet.Range("BC3:BC25").PasteSpecial Paste:=xlPasteValues
                    Else
                    End If
                Else
                End If
                ''''''''''''''''''''''''''''
                '''''''''ORIENTATION''''''''
                ''''''''''''''''''''''''''''
                If formsheet.Cells(cellnum, 4).Value = "A4" Then
                    If revisionsheet.Cells(3, 56).Value = "" Then
                        currExcelSheet.Range("N3:N25").Copy
                        revisionsheet.Range("BD3:BD25").PasteSpecial Paste:=xlPasteValues
                    Else
                    End If
                Else
                End If
            ''''''''''''''''''''''''''''
            '''''''''''''A5'''''''''''''
            ''''''''''''''''''''''''''''
                '''''''''''ROOFS''''''''''''
                ''''''''''''''''''''''''''''
                If formsheet.Cells(cellnum, 4).Value = "A5" Then
                    If revisionsheet.Cells(3, 2).Value = "" Then
                        currExcelSheet.Range("K3:K25").Copy
                        revisionsheet.Range("BE3:BE25").PasteSpecial Paste:=xlPasteValues
                        Dim BE As Range
                        For Each BE In revisionsheet.Range("BE3:BE25")
                        BE = Replace(BE, " ", "")
                        Next
                    Else
                    End If
                Else
                End If
                '''''''''''MODULES''''''''''
                ''''''''''''''''''''''''''''
                If formsheet.Cells(cellnum, 4).Value = "A5" Then
                    If revisionsheet.Cells(3, 58).Value = "" Then
                        currExcelSheet.Range("L3:L25").Copy
                        revisionsheet.Range("BF3:BF25").PasteSpecial Paste:=xlPasteValues
                    Else
                    End If
                Else
                End If
                ''''''''''''''''''''''''''''
                ''''''''''''PITCH'''''''''''
                ''''''''''''''''''''''''''''
                If formsheet.Cells(cellnum, 4).Value = "A5" Then
                    If revisionsheet.Cells(3, 59).Value = "" Then
                        currExcelSheet.Range("M3:M25").Copy
                        revisionsheet.Range("BG3:BG25").PasteSpecial Paste:=xlPasteValues
                    Else
                    End If
                Else
                End If
                ''''''''''''''''''''''''''''
                '''''''''ORIENTATION''''''''
                ''''''''''''''''''''''''''''
                If formsheet.Cells(cellnum, 4).Value = "A5" Then
                    If revisionsheet.Cells(3, 60).Value = "" Then
                        currExcelSheet.Range("N3:N25").Copy
                        revisionsheet.Range("BH3:BH25").PasteSpecial Paste:=xlPasteValues
                    Else
                    End If
                Else
                End If
    
    xlapp.DisplayAlerts = False
    'wkb.SaveAs (path3)
    Set formsheet = Nothing
    Set currExcelSheet = Nothing
    Set revisionsheet = Nothing

    wkb.Close savechanges:=True
    Set wkb = Nothing

    xlapp.Application.Quit
    Set xlapp = Nothing
End Function

Attribute VB_Name = "Module2"
Sub updateapps()

    Dim I As Integer
        For I = 0 To 3
            Call revisionfxn(31 - I)
        Next I
        
End Sub

Sub revisionfxn(cellnum)



''''''''''''''''''''''''''''''''''''''''''''''''''''''''''''
'''''''''''''''''''''''DECLARE VARIABLES''''''''''''''''''''
''''''''''''''''''''''''''''''''''''''''''''''''''''''''''''
Dim path1 As String
Dim path2 As String
Dim path3 As String
path1 = ThisDrawing.Path 'GETS THE FOLDER EXTENSION THE DRAWING IS IN
path2 = "\ACAD CALC TEMPLATE.xlsx"
path3 = path1 + path2
Dim xlapp As Object
Dim wkb As Object
Dim formsheet As Object
Dim currExcelSheet As Object
Dim revisionsheet As Object
Dim currentequipment As String
Dim alphaArray() As Variant
Dim revArray() As Variant
Dim numArray1() As Variant
Dim numArray2() As Variant
    '''''''''''''''''''''''''''''''''''''''''''''''''''''''''''''''''''''''''''''''
    ''''''''''''''''''SETUP EXCEL WORKBOOK AND EXCEL SHEETS''''''''''''''''''''''''
    '''''''''''''''''''''''''''''''''''''''''''''''''''''''''''''''''''''''''''''''
    Set xlapp = Excel.Application
    Set wkb = xlapp.Workbooks.Open(path3)
    xlapp.Visible = False
    Set formsheet = Excel.Application.Sheets("FORM")

    Set revisionsheet = Excel.Application.Sheets("REVISION LIST")
    alphaArray = Array("B", "F", "J", "N", "R", "V", "Z", "AD", "AH", "AL", "AP", "AT", "AX", "BB", "BF")
    revArray = Array("P1", "P2", "P3", "P4", "P5", "R1", "R2", "R3", "R4", "R5", "A1", "A2", "A3", "A4", "A5")
    numArray1 = Array(2, 6, 10, 14, 18, 22, 26, 30, 34, 38, 42, 46, 50, 54, 58)
    numArray2 = Array(46, 47, 48, 49, 50, 51, 52, 53, 54, 55, 56, 57, 58, 59, 60)
    
    For j = 0 To 14
        If formsheet.Cells(cellnum, 4).Value = revArray(j) Then
         If revisionsheet.Cells(45, numArray1(j)).Value = "" Then
            ThisDrawing.SummaryInfo.GetCustomByKey "currEquipment", currentequipment
            arraynum = alphaArray(j)
            For k = 0 To 14
                arrayrev = arraynum & numArray2(k)
                If revisionsheet.Range(arrayrev).Value = "" Then
                    revisionsheet.Range(arrayrev).Value = currentequipment
                    Exit For
                Else
                End If
            Next k
         Else
         End If
        Else
        End If
    Next j
       
    xlapp.DisplayAlerts = False
    Set formsheet = Nothing
    Set currExcelSheet = Nothing
    Set revisionsheet = Nothing

    wkb.Close savechanges:=True
    Set wkb = Nothing

    xlapp.Application.Quit
    Set xlapp = Nothing
End Sub
Sub newrev()
    Dim I As Integer
        For I = 0 To 3
            Call newrevfxn(31 - I)
        Next I
End Sub
Sub newrevfxn(cellnum)
Dim path1 As String
Dim path2 As String
Dim path3 As String
Dim revArray() As Variant
Dim numArray1() As Variant
path1 = ThisDrawing.Path 'GETS THE FOLDER EXTENSION THE DRAWING IS IN
path2 = "\ACAD CALC TEMPLATE.xlsx"
path3 = path1 + path2
Dim xlapp As Object
Dim wkb As Object
Dim formsheet As Object
Dim currExcelSheet As Object
Dim revisionsheet As Object
Dim currentequipment As String
Set xlapp = Excel.Application
    Set wkb = xlapp.Workbooks.Open(path3)
    xlapp.Visible = False
    Set formsheet = Excel.Application.Sheets("FORM")
    Set revisionsheet = Excel.Application.Sheets("REVISION LIST")
    revArray = Array("P1", "P2", "P3", "P4", "P5", "R1", "R2", "R3", "R4", "R5", "A1", "A2", "A3", "A4", "A5")
    numArray1 = Array(2, 6, 10, 14, 18, 22, 26, 30, 34, 38, 42, 46, 50, 54, 58)
    
    For j = 0 To 14
        If formsheet.Cells(cellnum, 4).Value = revArray(j) Then
            If revisionsheet.Cells(45, numArray1(j)).Value = "" Then
                revisionsheet.Cells(45, numArray1(j)).Value = "DONE"
            Else
            End If
        Else
        End If
    Next j

xlapp.DisplayAlerts = False
    Set formsheet = Nothing
    Set currExcelSheet = Nothing
    Set revisionsheet = Nothing

    wkb.Close savechanges:=True
    Set wkb = Nothing

    xlapp.Application.Quit
    Set xlapp = Nothing
End Sub
