(defun c:rack()
	(setq rafterSpacing (getreal "Rafter Spacing : "))
	(if(= (getvar "lunits") 2);decimal
		(setq
			spacing (/ rafterSpacing 12)
		)
		(if(= (getvar "lunits") 4);architectural
			(setq
				spacing rafterSpacing
			)
			(progn
				(alert "Units Must be Decimal or architectural")
				(exit)				
			)
		)		
	)
	(if (= (getvar "clayer") "0")
		(command "-layer" "off" "0" "yes" "")
		(command "-layer" "off" "0" "")
	)
	(defun pickRoofs( / *error*)
		(defun *error* (msg)
			(setvar "osmode" oldsnap)
			(setvar "cmdecho" oldecho)
			(setvar "clayer" oldLay)
			(command-s "undo" "end")
		)
	
		(setq oldEcho (getvar "cmdecho"))
		(setvar "cmdecho" 0)
		(setq oldSnap (getvar "osmode"))
		(setq oldLay(getvar "cLayer"))
		(setvar "osmode" 0)
		
		(command "undo" "begin")
		(prompt "\nSelect Entire House : ")
		(setq house (ssget))
		(command "-layer" "new" "temp2113" "")
		(command "-layer" "new" "Rafters" "")
		(command "-copytolayer" house "" "temp2113"'(0 0 0) '(0 0 0))
		(setq houseCopy (ssget "x" '((8 . "temp2113"))))
		(command "move" houseCopy "" "0,0,1e99" "")
		(command "move" houseCopy "" "0,0,-1e99" "")
		
		(while 
			(setq pt(getpoint "Select Roof : "))
			(progn
				(setvar "osmode" 128)
				(command "line" pt pause "")
				(setvar "osmode" 0)
				(setq ang (rtd(angle pt (cdr(assoc 11(entget(entlast)))))))
				(entdel(entlast))
				(command "-hatch" pt "p" "u" ang spacing "n" "")
				(command "-layer" "on" "0" "")
				(command "chprop" "l" "" "la" "Rafters" "")
				(if (= (getvar "clayer") "0")
					(command "-layer" "off" "0" "yes" "")
					(command "-layer" "off" "0" "")
				) 
				(command "explode" "l")
				(setq rafter (ssget "p"))
				(command "chprop" rafter "" "color" "red" "LType" "Dashed" "ltScale" "10" "")
			
			)
		)
		
		(command "undo" "end")
		(setvar "cmdecho" oldecho)
		(setvar "osmode" oldSnap)
		(setvar "clayer" oldLay)
	)
	(pickRoofs)
	(command "-layer" "on" "0" "")
)
