(defun c:testdicts()
  (setq adoc (vla-get-activedocument (vlax-get-acad-object) ) )
  (setq obj (namedobjdict))
(setq d (dictsearch obj "ACAD_DATALINK"))
;;;  (setq dictobj (namedobjdict))
;;;  (princ dictobj)
;;;  (setq thing (entget dictobj))
  (princ (vlax-ldata-list d))
)
