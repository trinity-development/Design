(defun c:blockDWG()
  
(setq blknm "INTERCONNECTION_DYN_NEW")
(setq inter (getstring "Please describe Interconnection without spaces\n"))
(setq selectionset (ssget))
(setq insertionpoint (getpoint))
(command "-purge" "Blocks" blknm "No")
(command "_.-Block" blknm insertionpoint selectionset "")
(command "filedia" "0")
(command "-wBlock" (strcat "C:\\Users\\TamirLieber\\Desktop\\block_library\\" inter ".dwg") blknm '(0 0 0))
(command "filedia" "1")
(command "_.-insert" blknm insertionpoint "" "" "")
)
