;-----------------------------------------------------------------------------;
;-----------------------------------------------------------------------------;
;-------------ROTATES ROOF THEN SETS THE ROOF ID ANGLE TO 0-------------------;
;-----------------------------------------------------------------------------;
;-----------------------------------------------------------------------------;
;-----------------------------------------------------------------------------;
;-----MADE BY TAMIR LIEBER----------------------------------------------------;
;-----------------------------------------------------------------------------;

(defun c:rfrot()
  (vl-load-com)
  (progn
  (vl-cmdf "rotate" (ssget) "" PAUSE PAUSE PAUSE PAUSE PAUSE "")
  (c:rotid)
)
  )
