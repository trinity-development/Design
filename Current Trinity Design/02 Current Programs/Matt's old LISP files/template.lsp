(defun c:template()
	(defun dtr ( deg ) (* pi (/ deg 180.0)))
	(setq 
		oldFile (getvar "filedia")
		oldSnap (getvar "osmode")
		oldCmd (getvar "cmddia")
		oldEcho (getvar "cmdecho")
		count 0
		templateList'(
			((6952.07 16623.1 0.0) "NL1")
			((7879.74 16623.1 0.0) "NL2")
			((8807.4 16623.1 0.0) "NL3")
			((9735.07 16623.1 0.0) "NL4")
			((10662.7 16623.1 0.0) "NL5")
			((11590.4 16623.1 0.0) "NLM1")
			((12518.1 16623.1 0.0) "NLM2")
			((13445.7 16623.1 0.0) "NLM3")
			((14373.4 16623.1 0.0) "NLM4")
			((15301.1 16623.1 0.0) "NLM5")
			((6952.07 15882.3 0.0) "NB1")
			((7879.74 15882.3 0.0) "NB2")
			((8807.4 15882.3 0.0) "NB3")
			((9735.07 15882.3 0.0) "NB4")
			((10662.7 15882.3 0.0) "NB5")
			((11590.4 15882.3 0.0) "NBM1")
			((12518.1 15882.3 0.0) "NBM2")
			((13445.7 15882.3 0.0) "NBM3")
			((14373.4 15882.3 0.0) "NBM4")
			((15301.1 15882.3 0.0) "NBM5")
			((6952.07 15141.5 0.0) "NLC1")
			((7879.74 15141.5 0.0) "NLC2")
			((8807.4 15141.5 0.0) "NLC21C")
			((9735.07 15141.5 0.0) "NBC1")
			((10662.7 15141.5 0.0) "NBC2")
			((11590.4 15141.5 0.0) "NBC21C")
			
			((17665.8 16623.1 0.0) "UL1")
			((18593.5 16623.1 0.0) "UL2")
			((19521.1 16623.1 0.0) "UL3")
			((20448.8 16623.1 0.0) "UL4")
			((21376.5 16623.1 0.0) "UL5")
			((22304.1 16623.1 0.0) "ULM1")
			((23231.8 16623.1 0.0) "ULM2")
			((24159.5 16623.1 0.0) "ULM3")
			((25087.1 16623.1 0.0) "ULM4")
			((26014.8 16623.1 0.0) "ULM5")
			((17665.8 15882.3 0.0) "UB1")
			((18593.5 15882.3 0.0) "UB2")
			((19521.1 15882.3 0.0) "UB3")
			((20448.8 15882.3 0.0) "UB4")
			((21376.5 15882.3 0.0) "UB5")
			((22304.1 15882.3 0.0) "UBM1")
			((23231.8 15882.3 0.0) "UBM2")
			((24159.5 15882.3 0.0) "UBM3")
			((25087.1 15882.3 0.0) "UBM4")
			((26014.8 15882.3 0.0) "UBM5")
			((17665.8 15141.5 0.0) "ULC1")
			((18593.5 15141.5 0.0) "ULC2")
			((19521.1 15141.5 0.0) "ULC21C")
			((20448.8 15141.5 0.0) "UBC1")
			((21376.5 15141.5 0.0) "UBC2")
			((22304.1 15141.5 0.0) "UBC21C")
			
			((7647.18 22196.2 0.0) "TL1CAC")
			((8574.85 22196.2 0.0) "TL1AC")
			((9502.51 22196.2 0.0) "TL2AC")
			((10430.2 22196.2 0.0) "TL3AC")
			((7647.18 21455.4 0.0) "TB1CAC")
			((8574.85 21455.4 0.0) "TB1AC")
			((9502.51 21455.4 0.0) "TB2AC")
			((10430.2 21455.4 0.0) "TB3AC")
			
			((12330.5 22196.2 0.0) "TL1DC")
			((13209.3 22196.2 0.0) "TB1DC")
			((12330.5 21455.4 0.0) "TL1DCSS")
			((13209.3 21455.4 0.0) "TB1DCSS")
			
			((14741.1 22196.2 0.0) "TL1CDC")
			((15619.9 22196.2 0.0) "TB1CDC")
			((14741.1 21455.4 0.0) "TL1CDCSS")
			((15619.9 21455.4 0.0) "TB1CDCSS")


		)
	)
	(setvar "cmdecho" 0)
	(setvar "filedia" 0)
	(setvar "osmode" 0)
	(setvar "cmddia" 0)
	(while
		(< count (length templateList))
		(progn	
			(setq
				template (nth count templateList)
				path (strcat "Z:\\1. RESIDENTIAL JOBS\\006 Block Library\\3LINE TEMPLATES\\" (nth 1 template) ".dwg")
				basePoint (nth 0 template)
				;;;
				secondPoint (polar basePoint (dtr 216) 1018.25)
				;;;
			)
			(if
				(findfile path)
				(command "wblock" path  "Y" "" basePoint "c" basepoint secondPoint "" "N")
				(command "wblock" path "" basePoint "c" basepoint secondPoint "" "N")
				
			)
			(command "undo" "1")
			(setq
				count (+ 1 count)
			)
		)
	)
	(setvar "filedia" oldFile)
	(setvar "osmode" oldSnap)
	(setvar "cmddia" oldCmd)
	(setvar "cmdecho" oldEcho)
	(princ)
)
