(vl-load-com)

(load "3line")
(load "UPDATEBLOCKS")
(load "copyPasteIt")
(load "fixOS")
(load "panelMax")
(load "plotSet")
(load "systemspecs.lsp")

(load "scaleID.lsp")
(load "chromic3.lsp")
(load "chromic3old.lsp")
(load "countblock.lsp")
(load "countblockr.lsp")
(load "getroofs.lsp")
(load "getroofs(7-30-18).lsp")
(load "rooftext.lsp")
(load "rooftext(7-30-18).lsp")
(load "quickblock.lsp")
(load "getsnaproofs.lsp")
(load "makeblock.lsp")
(load "makeroofs.lsp")
(load "quickblock.lsp")
(load "revisionlist.lsp")
(load "Chromic5.lsp")
(load "revisioncount.lsp")
(load "RevisionSnapCount.lsp")
(load "roofrotate.lsp")
(load "rotationID.lsp")
(load "updateapps.lsp")
(load "appscheck.lsp")
(load "getoldgenesis.lsp")
(load "oldgenesis.lsp")
(load "protomakeblock.lsp")
(load "scale")
(load "top")
(load "update.lsp")
(load "genesis.lsp")
(load "gene_draw.lsp")
(load "getnewarray.lsp")
(load "newarray.lsp")
(load "CSharpUpdateApps.lsp")
(load "3lineUpdate.lsp")
(load "onRun")

;(load "prelim")
